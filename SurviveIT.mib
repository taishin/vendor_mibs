SurviveIT-Alarm-MIB DEFINITIONS ::= BEGIN

	IMPORTS
		enterprises    FROM RFC1065-SMI
		OBJECT-TYPE    FROM RFC-1212
		TRAP-TYPE      FROM RFC-1215;
		
		cheyenne            OBJECT IDENTIFIER ::= { enterprises 46 }
		SurviveIT             OBJECT IDENTIFIER ::= { cheyenne 884 }
        SurviveITNLMRev       OBJECT IDENTIFIER ::= { SurviveIT 1 }

-- *************************************************************************
-- SurviveIT (1.3.6.1.4.1.46.884)
-- **************************************************************************
SurviveITNLMRevMajor OBJECT-TYPE
	SYNTAX INTEGER (0..65535)
	ACCESS read-only
	STATUS mandatory
	DESCRIPTION
		"The major revision level of the NLM (left of the decimal).
		Used for presence checking."
	::= { SurviveITNLMRev 1 }

SurviveITNLMRevMinor OBJECT-TYPE
	SYNTAX INTEGER (0..65535)
	ACCESS read-only
	STATUS mandatory
	DESCRIPTION
		"The minor revision level of the NLM (right of the decimal)."
	::= { SurviveITNLMRev 2 }

SurviveITParmsTrapEnable OBJECT-TYPE
	SYNTAX INTEGER (0..1)
	ACCESS read-write
	STATUS mandatory
	DESCRIPTION
		"Indicates whether agent should or should not send traps."
	::= { SurviveIT 2 }

SurviveITParmsPollTime OBJECT-TYPE
	SYNTAX INTEGER (60..2592000)
	ACCESS read-write
	STATUS mandatory
	DESCRIPTION
		"Seconds between checking for traps."
	::= { SurviveIT 3 }

SurviveITServerName OBJECT-TYPE
                SYNTAX OCTET STRING
                ACCESS read-only
                STATUS mandatory
                DESCRIPTION
                        "NetWare Server Which Generated Error"
                ::= {SurviveIT 4}        
        
SurviveITtrapdesc   OBJECT-TYPE
                SYNTAX OCTET STRING
                ACCESS read-only
                STATUS optional
                DESCRIPTION
                        "A description of a specific Cheyenne trap"
                ::= {SurviveIT 5}        
        
-- *************************************************************************
-- traps
-- **************************************************************************
SurviveITtrapHigh                TRAP-TYPE       
	        		ENTERPRISE	SurviveIT
                                VARIABLES       {
                                                SurviveITServerName,
                                                SurviveITtrapdesc
                                                }
        			DESCRIPTION
                                        "SurviveIT Critical Trap."
                                --#TYPE "SurviveIT Critical"
                                --#SUMMARY "%s  SurviveIT: %s "
                                --#ARGUMENTS {0,1}
                                --#SEVERITY CRITICAL
                                --#STATE   DEGRADED     
	        	        ::= 1
SurviveITtrapMed                 TRAP-TYPE       
	        		ENTERPRISE	SurviveIT
                                VARIABLES       {
                                                SurviveITServerName,
                                                SurviveITtrapdesc
                                                }
        			DESCRIPTION
                                        "SurviveIT Minor Trap"
                                --#TYPE "SurviveIT Warning"
                                --#SUMMARY "%s  SurviveIT: %s "
                                --#ARGUMENTS {0,1}
                                --#SEVERITY MINOR
                                --#TIMEINDEX 1
                                --#STATE   OPERATIONAL     
	        	        ::= 2
SurviveITtrapLow                 TRAP-TYPE       
	        		ENTERPRISE	SurviveIT
                                VARIABLES       {
                                                SurviveITServerName,
                                                SurviveITtrapdesc
                                                }
        			DESCRIPTION
                                        "SurviveIT Informational Trap"
                                --#TYPE "SurviveIT Informational"
                                --#SUMMARY "%s  SurviveIT: %s "
                                --#ARGUMENTS {0,1}
                                --#SEVERITY INFORMATIONAL
                                --#STATE   OPERATIONAL     
	        	        ::= 3
END
