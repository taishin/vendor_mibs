NS-ROOT-MIB DEFINITIONS ::= BEGIN

IMPORTS
	Counter32, Gauge32, Integer32, IpAddress, NOTIFICATION-TYPE,OBJECT-TYPE, TimeTicks, enterprises, MODULE-IDENTITY, OBJECT-IDENTITY
		FROM SNMPv2-SMI
	Ipv6Address
		FROM IPV6-TC
	 InetAddressType, InetAddress
		FROM INET-ADDRESS-MIB;

netScaler MODULE-IDENTITY
	LAST-UPDATED "201003120000Z"
	ORGANIZATION "Citrix Systems, Inc."
	CONTACT-INFO  "Citrix Technical Assistance Center
			Postal: Citrix Systems, Inc.
				851 West Cypress Creek Road
				Fort Lauderdale, Florida  33309
				United States
			Tel: +1-800-4-CITRIX (+1-800-424-8749)
			E-mail: customercare@citrix.com"
	DESCRIPTION "The enterprise specific MIB for Netscaler NS9.1."
	::= { enterprises 5951 }

nsRoot OBJECT IDENTIFIER
    ::= { netScaler 1 }

netScalerEvents OBJECT IDENTIFIER
    ::= { nsRoot 1 }

wsSystem OBJECT IDENTIFIER
    ::= { nsRoot 2 }

sysStatistics OBJECT IDENTIFIER
    ::= { wsSystem 1 }

totalClientConnections OBJECT-TYPE
    SYNTAX      Counter32
    MAX-ACCESS  read-only
    STATUS      obsolete
    DESCRIPTION 
        "The Total Client Connections made from system start.

	This object is obsolete."
    ::= { sysStatistics 1 }

curClientConnections OBJECT-TYPE
    SYNTAX      Counter32
    MAX-ACCESS  read-only
    STATUS      obsolete
    DESCRIPTION 
        "The Current Client Connections.

	This object is obsolete.It can be measured through nsTcpStatsGroup.tcpCurClientConn."
    ::= { sysStatistics 2 }

totalServerConnections OBJECT-TYPE
    SYNTAX      Counter32
    MAX-ACCESS  read-only
    STATUS      obsolete
    DESCRIPTION 
        "The Total Server Connections made from system start.

	This object is obsolete."
    ::= { sysStatistics 3 }

curServerConnections OBJECT-TYPE
    SYNTAX      Counter32
    MAX-ACCESS  read-only
    STATUS      obsolete
    DESCRIPTION 
        "The Current Server Connections.

	This object is obsolete.It can be measured through nsTcpStatsGroup.tcpCurServerConn."
    ::= { sysStatistics 4 }

clientConnRefused OBJECT-TYPE
    SYNTAX      Counter32
    MAX-ACCESS  read-only
    STATUS      obsolete
    DESCRIPTION 
        "Client connections added the SurgeQ, and blocked from initiating a server connection to control op/s.

	This object is obsolete."
    ::= { sysStatistics 5 }

reuseHit OBJECT-TYPE
    SYNTAX      Counter32
    MAX-ACCESS  read-only
    STATUS      obsolete
    DESCRIPTION 
        "Total no of client transactions used the server connection in the reuse-pool.

	This object is obsolete.It can be measured through nsTcpStatsGroup.tcpReuseHit."
    ::= { sysStatistics 6 }

reuseMiss OBJECT-TYPE
    SYNTAX      Counter32
    MAX-ACCESS  read-only
    STATUS      obsolete
    DESCRIPTION 
        "The total new Connections made, when server connection
         unavailable in reuse pool...OBSOLETE"
    ::= { sysStatistics 7 }

totClientDontReuse OBJECT-TYPE
    SYNTAX      Counter32
    MAX-ACCESS  read-only
    STATUS      obsolete
    DESCRIPTION 
        "The total client connection with Dont Reuse flag set...OBSOLETE"
    ::= { sysStatistics 8 }

totServerDontReuse OBJECT-TYPE
    SYNTAX      Counter32
    MAX-ACCESS  read-only
    STATUS      obsolete
    DESCRIPTION 
        "The total server connection with Dont Reuse set...OBSOLETE"
    ::= { sysStatistics 9 }

curPhysicalServers OBJECT-TYPE
    SYNTAX      Counter32
    MAX-ACCESS  read-only
    STATUS      obsolete
    DESCRIPTION 
        "The number of physical servers that WS has open connections with.

	This object is obsolete.It can be measured through nsTcpStatsGroup.tcpCurPhysicalServers."
    ::= { sysStatistics 10 }

totPhysicalServers OBJECT-TYPE
    SYNTAX      Counter32
    MAX-ACCESS  read-only
    STATUS      obsolete
    DESCRIPTION 
        "The total number of physical servers that WS opened connections 
         to from the last reboot.

	This object is obsolete."
    ::= { sysStatistics 11 }

cookiePacketSeqReject OBJECT-TYPE
    SYNTAX      Counter32
    MAX-ACCESS  read-only
    STATUS      obsolete
    DESCRIPTION 
        "The number of tcp connections rejected because of syn cookie sequence number mismatch.

	This object is obsolete.It can be measured through nsTcpStatsGroup.tcpErrCookiePktSeqReject."
    ::= { sysStatistics 12 }

cookieSignatureReject OBJECT-TYPE
    SYNTAX      Counter32
    MAX-ACCESS  read-only
    STATUS      obsolete
    DESCRIPTION 
        "The number of tcp connections rejected because of syn cookie mismatch.

	This object is obsolete.It can be measured through nsTcpStatsGroup.tcpErrCookiePktSigReject."
    ::= { sysStatistics 13 }

cpuUsage OBJECT-TYPE
    SYNTAX      Counter32
    MAX-ACCESS  read-only
    STATUS      obsolete
    DESCRIPTION 
        "The CPU Utilization.

	This object is obsolete."
    ::= { sysStatistics 14 }

unackSyn OBJECT-TYPE
    SYNTAX      Counter32
    MAX-ACCESS  read-only
    STATUS      obsolete
    DESCRIPTION 
        "The number of un-acknowledged SYNs NS has received so far.

	This object is obsolete.It can be calculated as (tcpTotSyn - tcpTotClientConnOpened)."
    ::= { sysStatistics 15 }

curClientEstablishedConn OBJECT-TYPE
    SYNTAX      Counter32
    MAX-ACCESS  read-only
    STATUS      obsolete
    DESCRIPTION 
        "The number of currently established client connections.

	This object is obsolete.It can be measured through nsTcpStatsGroup.tcpCurClientConnEstablished."
    ::= { sysStatistics 16 }

curServerEstablishedConn OBJECT-TYPE
    SYNTAX      Counter32
    MAX-ACCESS  read-only
    STATUS      obsolete
    DESCRIPTION 
        "The number of currently established server connections.

	This object is obsolete.It can be measured through nsTcpStatsGroup.tcpCurServerConnEstablished."
    ::= { sysStatistics 17 }

wsHttpGroup OBJECT IDENTIFIER
	::= { sysStatistics 18 }

totalRequests OBJECT-TYPE
    SYNTAX      Counter32
    MAX-ACCESS  read-only
    STATUS      obsolete
    DESCRIPTION 
        "The total HTTP Requests."
    ::= { wsHttpGroup 1 }

totalGets OBJECT-TYPE
    SYNTAX      Counter32
    MAX-ACCESS  read-only
    STATUS      obsolete
    DESCRIPTION 
        "The total HTTP GETs."
    ::= { wsHttpGroup 2 }

totalRequests1-0 OBJECT-TYPE
    SYNTAX      Counter32
    MAX-ACCESS  read-only
    STATUS      obsolete
    DESCRIPTION 
        "The total HTTP 1.0 Requests."
    ::= { wsHttpGroup 3 }

totalPosts OBJECT-TYPE
    SYNTAX      Counter32
    MAX-ACCESS  read-only
    STATUS      obsolete
    DESCRIPTION 
        "The total HTTP Posts."
    ::= { wsHttpGroup 4 }

totalResponses OBJECT-TYPE
    SYNTAX      Counter32
    MAX-ACCESS  read-only
    STATUS      obsolete
    DESCRIPTION 
        "The total HTTP Responses."
    ::= { wsHttpGroup 5 }

totalResponses1-0 OBJECT-TYPE
    SYNTAX      Counter32
    MAX-ACCESS  read-only
    STATUS      obsolete
    DESCRIPTION 
        "The total HTTP 1.0 Responses."
    ::= { wsHttpGroup 6 }

totalContentLenResponses OBJECT-TYPE
    SYNTAX      Counter32
    MAX-ACCESS  read-only
    STATUS      obsolete
    DESCRIPTION 
        "The total HTTP Responses with Content Length."
    ::= { wsHttpGroup 7 }

totalChunkedResponses OBJECT-TYPE
    SYNTAX      Counter32
    MAX-ACCESS  read-only
    STATUS      obsolete
    DESCRIPTION 
        "The total HTTP Chunked Responses."
    ::= { wsHttpGroup 8 }

totalMultiPartResponses OBJECT-TYPE
    SYNTAX      Counter32
    MAX-ACCESS  read-only
    STATUS      obsolete
    DESCRIPTION 
        "The total HTTP Multi-part Responses."
    ::= { wsHttpGroup 9 }

totalIncompleteHeaders OBJECT-TYPE
    SYNTAX      Counter32
    MAX-ACCESS  read-only
    STATUS      obsolete
    DESCRIPTION 
        "The total HTTP Incomplete headers."
    ::= { wsHttpGroup 10 }

totalIncompleteRequests OBJECT-TYPE
    SYNTAX      Counter32
    MAX-ACCESS  read-only
    STATUS      obsolete
    DESCRIPTION 
        "The total Incomplete Requests."
    ::= { wsHttpGroup 11 }

totalIncompleteResponses OBJECT-TYPE
    SYNTAX      Counter32
    MAX-ACCESS  read-only
    STATUS      obsolete
    DESCRIPTION 
        "The total Incomplete Responses."
    ::= { wsHttpGroup 12 }

totalPipeLinedRequests OBJECT-TYPE
    SYNTAX      Counter32
    MAX-ACCESS  read-only
    STATUS      obsolete
    DESCRIPTION 
        "The total pipe-lined Requests."
    ::= { wsHttpGroup 13 }

serverBusyErrs OBJECT-TYPE
    SYNTAX      Counter32
    MAX-ACCESS  read-only
    STATUS      obsolete
    DESCRIPTION 
        "The total HTTP Server Busy Errors."
    ::= { wsHttpGroup 14 }

wsIfStatsTable OBJECT-TYPE
    SYNTAX      SEQUENCE OF WsIfStatsEntry
    MAX-ACCESS  not-accessible
    STATUS      obsolete
    DESCRIPTION 
        "The Raw bandwidth usage of all the interfaces.

	This Table is obsolete.Instead of this table use nsSysGroup.nsIfStatsTable."
    ::= { sysStatistics 19 }

wsIfStatsEntry OBJECT-TYPE
    SYNTAX      WsIfStatsEntry
    MAX-ACCESS  not-accessible
    STATUS      obsolete
    DESCRIPTION 
        "The Raw bandwidth usage of all the interfaces.

	This Entry is obsolete.Instead of this entry use nsSysGroup.nsIfStatsEntry."
    INDEX       { index }
    ::= { wsIfStatsTable 1 }

WsIfStatsEntry ::= SEQUENCE {
    index                       Integer32,
    wsIfName                    OCTET STRING,
    wsIfMedia                   OCTET STRING,
    rxRawBandwidthUsage         Counter32,
    rxAveragePacketRate         Counter32,
    rxCurrentPacketRate         Counter32,
    rxAveragePacketsSize        Counter32,
    rxFrameErrors               Counter32,
    rxCrcErrors                 Counter32,
    rxAlignmentErrors           Counter32,
    txRawBandwidthUsage         Counter32,
    txAveragePacketRate         Counter32,
    txCurrentPacketRate         Counter32,
    txAveragePacketsSize        Counter32,
    txExcessCollisions          Counter32,
    txLateCollisions            Counter32,
    txCollisions                Counter32,
    txMultiCollisionsErrors     Counter32,
    txCarrierErrors             Counter32
}

index OBJECT-TYPE
    SYNTAX      Integer32
    MAX-ACCESS  read-only
    STATUS      obsolete
    DESCRIPTION 
        "The distinguishing Id for each physical interface.

	This object is obsolete."
    ::= { wsIfStatsEntry 1 }

wsIfName OBJECT-TYPE
    SYNTAX      OCTET STRING
    MAX-ACCESS  read-only
    STATUS      obsolete
    DESCRIPTION 
        "The name of the Interface.

	This object is obsolete.It can be measured through nsIfStatsTable.ifName."
    ::= { wsIfStatsEntry 2 }

wsIfMedia OBJECT-TYPE
    SYNTAX      OCTET STRING
    MAX-ACCESS  read-only
    STATUS      obsolete
    DESCRIPTION 
        "The media type of the Interface.

	This object is obsolete.It can be measured through nsIfStatsTable.ifMedia."
    ::= { wsIfStatsEntry 3 }

rxRawBandwidthUsage OBJECT-TYPE
    SYNTAX      Counter32
    MAX-ACCESS  read-only
    STATUS      obsolete
    DESCRIPTION 
        "The received raw bandwidth on interface in bitsps
         since the last time this variable was 
         retrieved using SNMP.

	This object is obsolete."
    ::= { wsIfStatsEntry 4 }

rxAveragePacketRate OBJECT-TYPE
    SYNTAX      Counter32
    MAX-ACCESS  read-only
    STATUS      obsolete
    DESCRIPTION 
        "The average number of packets received on the 
         interface since the system start.

	This object is obsolete.It can be measured through nsIfStatsTable.ifRxAvgPacketRate."
    ::= { wsIfStatsEntry 5 }

rxCurrentPacketRate OBJECT-TYPE
    SYNTAX      Counter32
    MAX-ACCESS  read-only
    STATUS      obsolete
    DESCRIPTION 
        "The packet rate on the interface since the last
         time the variable was retrieved with using SNMP.

	This object is obsolete."
    ::= { wsIfStatsEntry 6 }

rxAveragePacketsSize OBJECT-TYPE
    SYNTAX      Counter32
    MAX-ACCESS  read-only
    STATUS      obsolete
    DESCRIPTION 
        "The average size of the packet received on the 
         interface since the system start.

	 This object is obsolete."
    ::= { wsIfStatsEntry 7 }

rxFrameErrors OBJECT-TYPE
    SYNTAX      Counter32
    MAX-ACCESS  read-only
    STATUS      obsolete
    DESCRIPTION 
        "A Counter for the number of frame errors received
         on the interface.

	This object is obsolete.It can be measured through nsIfStatsTable.ifRxFrameErrors."
    ::= { wsIfStatsEntry 8 }

rxCrcErrors OBJECT-TYPE
    SYNTAX      Counter32
    MAX-ACCESS  read-only
    STATUS      obsolete
    DESCRIPTION 
        "A Counter for the number of Crc errors received on
         the interface.

	This object is obsolete.It can be measured through nsIfStatsTable.ifRxCRCErrors."
    ::= { wsIfStatsEntry 9 }

rxAlignmentErrors OBJECT-TYPE
    SYNTAX      Counter32
    MAX-ACCESS  read-only
    STATUS      obsolete
    DESCRIPTION 
        "A Counter to indicate the number of Alignment errors
         received on the interface.

	This object is obsolete.It can be measured through nsIfStatsTable.ifRxAlignmentErrors."
    ::= { wsIfStatsEntry 10 }

txRawBandwidthUsage OBJECT-TYPE
    SYNTAX      Counter32
    MAX-ACCESS  read-only
    STATUS      obsolete
    DESCRIPTION 
        "The transmit raw bandwidth on interface in bitsps
         from the last time this variable was retrieved.

	This object is obsolete."
    ::= { wsIfStatsEntry 11 }

txAveragePacketRate OBJECT-TYPE
    SYNTAX      Counter32
    MAX-ACCESS  read-only
    STATUS      obsolete
    DESCRIPTION 
        "The average number of packets transmitted on the 
         the interface since the system start.

	This object is obsolete.It can be measured through nsIfStatsTable.ifTxAvgPacketRate."
    ::= { wsIfStatsEntry 12 }

txCurrentPacketRate OBJECT-TYPE
    SYNTAX      Counter32
    MAX-ACCESS  read-only
    STATUS      obsolete
    DESCRIPTION 
        "The packet rate on the interface since the last
         time this variable was retrieved using SNMP.

	This object is obsolete."
    ::= { wsIfStatsEntry 13 }

txAveragePacketsSize OBJECT-TYPE
    SYNTAX      Counter32
    MAX-ACCESS  read-only
    STATUS      obsolete
    DESCRIPTION 
        "The average size of the packet received on the 
         interface since the system start.

	This object is obsolete."
    ::= { wsIfStatsEntry 14 }

txExcessCollisions OBJECT-TYPE
    SYNTAX      Counter32
    MAX-ACCESS  read-only
    STATUS      obsolete
    DESCRIPTION 
        "A Counter to indicate excess collisions detected in
         transmission on the interface.

	This object is obsolete.It can be measured through nsIfStatsTable.ifTxExcessCollisions."
    ::= { wsIfStatsEntry 15 }

txLateCollisions OBJECT-TYPE
    SYNTAX      Counter32
    MAX-ACCESS  read-only
    STATUS      obsolete
    DESCRIPTION 
        "A Counter to indicate late collisions detected in
         transmission on the interface.

	This object is obsolete.It can be measured through nsIfStatsTable.ifTxLateCollisions."
    ::= { wsIfStatsEntry 16 }

txCollisions OBJECT-TYPE
    SYNTAX      Counter32
    MAX-ACCESS  read-only
    STATUS      obsolete
    DESCRIPTION 
        "A Counter to indicate total collision Errors detected 
         in transmission on the interface.

	This object is obsolete.It can be measured through nsIfStatsTable.ifTxCollisions."
    ::= { wsIfStatsEntry 17 }

txMultiCollisionsErrors OBJECT-TYPE
    SYNTAX      Counter32
    MAX-ACCESS  read-only
    STATUS      obsolete
    DESCRIPTION 
        "A Counter to indicate Multi collision Errors detected 
         in transmission on the interface.

	This object is obsolete.It can be measured through nsIfStatsTable.ifTxMultiCollisionsErrors."
    ::= { wsIfStatsEntry 18 }

txCarrierErrors OBJECT-TYPE
    SYNTAX      Counter32
    MAX-ACCESS  read-only
    STATUS      obsolete
    DESCRIPTION 
        "A Counter to indicate Carrier Errors detected in 
         transmission on the interface.

	This object is obsolete.It can be measured through nsIfStatsTable.ifTxCarrierErrors."
    ::= { wsIfStatsEntry 19 }

wsudpgroup OBJECT IDENTIFIER
    ::= { sysStatistics 20 }

totudpsessions OBJECT-TYPE
    SYNTAX      Counter32
    MAX-ACCESS  read-only
    STATUS      obsolete
    DESCRIPTION 
        "Total number of udp sessions since the start of the system"
    ::= { wsudpgroup 1 }

currudpsessions OBJECT-TYPE
    SYNTAX      Counter32
    MAX-ACCESS  read-only
    STATUS      obsolete
    DESCRIPTION 
        "Total number of current udp sessions "
    ::= { wsudpgroup 2 }

sysConfig OBJECT IDENTIFIER
    ::= { wsSystem 2 }

wsIpAddress OBJECT-TYPE
    SYNTAX      IpAddress
    MAX-ACCESS  read-only
    STATUS      obsolete
    DESCRIPTION 
        "The primary IP address of the netscaler.

	This object is obsolete.It can be measured through nsSysGroup.sysIpAdress."
    ::= { sysConfig 1 }

wsNetmask OBJECT-TYPE
    SYNTAX      IpAddress
    MAX-ACCESS  read-only
    STATUS      obsolete
    DESCRIPTION 
        "The netmask for the IP address of the netscaler.

	This object is obsolete.It can be measured through nsSysGroup.sysNetmask."
    ::= { sysConfig 2 }

wsMappedIpAddress OBJECT-TYPE
    SYNTAX      IpAddress
    MAX-ACCESS  read-only
    STATUS      obsolete
    DESCRIPTION 
        "The Mapped IP address of the netscaler."
    ::= { sysConfig 3 }

wsLastMappedIpAddress OBJECT-TYPE
    SYNTAX      IpAddress
    MAX-ACCESS  read-only
    STATUS      obsolete
    DESCRIPTION 
        "The last Mapped IP address of the netscaler."
    ::= { sysConfig 4 }

wsMappedIpAddressRange OBJECT-TYPE
    SYNTAX      Integer32
    MAX-ACCESS  read-only
    STATUS      obsolete
    DESCRIPTION 
        "The range of mapped IP addresses on the netscaler."
    ::= { sysConfig 5 }

wsFailOver OBJECT-TYPE
    SYNTAX      INTEGER { enabled(1), disabled(2) }
    MAX-ACCESS  read-only
    STATUS      obsolete
    DESCRIPTION 
        "Is Fail Over enabled on the netscaler.

	This object is obsolete."
    ::= { sysConfig 6 }

wsPriority OBJECT-TYPE
    SYNTAX      Integer32
    MAX-ACCESS  read-only
    STATUS      obsolete
    DESCRIPTION 
        "The priority of the netscaler."
    ::= { sysConfig 7 }

wsMaxClientList OBJECT-TYPE
    SYNTAX      Integer32
    MAX-ACCESS  read-only
    STATUS      obsolete
    DESCRIPTION 
        "The Maximum number of server connections that NS can open to the server.

	This object is obsolete."
    ::= { sysConfig 8 }

wsClientIp OBJECT-TYPE
    SYNTAX      INTEGER { enabled(1), disabled(2) }
    MAX-ACCESS  read-only
    STATUS      obsolete
    DESCRIPTION 
        "Enable Client IP in the HTTP Request to the Server.
	
	This object is obsolete."
    ::= { sysConfig 9 }

wsFailoverTime OBJECT-TYPE
    SYNTAX      Integer32
    MAX-ACCESS  read-only
    STATUS      obsolete
    DESCRIPTION 
        "The time in seconds after which the secondary takes over as 
         primary, if there is no response from primary."
    ::= { sysConfig 10 }

wsMaxRequestsPerConn OBJECT-TYPE
    SYNTAX      Integer32
    MAX-ACCESS  read-only
    STATUS      obsolete
    DESCRIPTION 
        "The Maximum number of requests per connection on a server-connection.

	This object is obsolete."
    ::= { sysConfig 11 }

wsSmoothConnection OBJECT-TYPE
    SYNTAX      INTEGER { enabled(1), disabled(2) }
    MAX-ACCESS  read-only
    STATUS      obsolete
    DESCRIPTION 
        "Smooth Connection Feature on the netscaler.

	This object is obsolete."
    ::= { sysConfig 12 }

loadBalancing OBJECT IDENTIFIER
    ::= { nsRoot 3 }

lbStatisticsTable OBJECT-TYPE
    SYNTAX      SEQUENCE OF LbStatisticsEntry
    MAX-ACCESS  not-accessible
    STATUS      obsolete
    DESCRIPTION 
        "The Virtual Service Information for each of the entities.

	This Table is obsolete.Instead of this table use nsVserverGroup.vserverTable."
    ::= { loadBalancing 1 }

lbStatisticsEntry OBJECT-TYPE
    SYNTAX      LbStatisticsEntry
    MAX-ACCESS  not-accessible
    STATUS      obsolete
    DESCRIPTION 
        "The Virtual Service Information for each of the entities.

	This Entry is obsolete.Instead of this entry use nsVserverGroup.vserverEntry."
    INDEX       { vsId, psId }
    ::= { lbStatisticsTable 1 }

LbStatisticsEntry ::= SEQUENCE {
    vsId            Integer32,
    psId            Integer32,
    vsIpAddress     IpAddress,
    vsPort          Integer32,
    psIpAddress     IpAddress,
    psPort          Integer32,
    protocolType    INTEGER,
    lbMethod		INTEGER,
    serviceHits     Integer32,
    latency         Integer32,
    connections		Integer32

}

vsId OBJECT-TYPE
    SYNTAX      Integer32
    MAX-ACCESS  read-only
    STATUS      obsolete
    DESCRIPTION 
        "The distinguishing Id for each Virtual Service inside
         a NetScaler.

	This object is obsolete."
    ::= { lbStatisticsEntry 1 }

psId OBJECT-TYPE
    SYNTAX      Integer32
    MAX-ACCESS  read-only
    STATUS      obsolete
    DESCRIPTION 
        "The distinguishing Id for each Physical Service inside
         a NetScaler.

	This object is obsolete."
    ::= { lbStatisticsEntry 2 }

vsIpAddress OBJECT-TYPE
    SYNTAX      IpAddress
    MAX-ACCESS  read-only
    STATUS      obsolete
    DESCRIPTION 
        "The IP address in the Virtual Service.

	This object is obsolete.It can be measured through vserverTable.vsvrIpAddress."
    ::= { lbStatisticsEntry 3 }

vsPort OBJECT-TYPE
    SYNTAX      Integer32
    MAX-ACCESS  read-only
    STATUS      obsolete
    DESCRIPTION 
        "The port in the Virtual Service.

	This object is obsolete.It can be measured through vserverTable.vsvrPort."
    ::= { lbStatisticsEntry 4 }

psIpAddress OBJECT-TYPE
    SYNTAX      IpAddress
    MAX-ACCESS  read-only
    STATUS      obsolete
    DESCRIPTION 
        "The IP address in the Physical Service.

	This object is obsolete.It can be measured through serviceTable.svcIpAddress."
    ::= { lbStatisticsEntry 5 }

psPort OBJECT-TYPE
    SYNTAX      Integer32
    MAX-ACCESS  read-only
    STATUS      obsolete
    DESCRIPTION 
        "The port in the Physical Service.

	This object is obsolete.It can be measured through serviceTable.svcPort."
    ::= { lbStatisticsEntry 6 }

protocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type in the Virtual Service.

	This object is obsolete.It can be measured through vserverTable.vsvrType."
    ::= { lbStatisticsEntry 7 }

lbMethod OBJECT-TYPE
	SYNTAX INTEGER	{
		weightedRoundRobin(1), leastConnections(2), leastResponse(3),
		asynchronousMAC(4), urlHashed(5), domainHashed(6),
		destinationIPHashed(7), sourceIPHashed(8), leastBandwidth(9),
		leastPackets(10) }
		MAX-ACCESS read-only
		STATUS obsolete
		DESCRIPTION
			"The Policy used for Load Balancing.

			This object is obsolete.It can be measured through lbvserverTable.lbvsvrLBMethod."
		::= { lbStatisticsEntry 8 }

serviceHits OBJECT-TYPE
    SYNTAX      Integer32
    MAX-ACCESS  read-only
    STATUS      obsolete
    DESCRIPTION 
        "The total hits on the physical service.

	This object is obsolete.It can be measured through vserverTable.vsvrTotalRequests."
    ::= { lbStatisticsEntry 9 }

latency OBJECT-TYPE
    SYNTAX      Integer32
    MAX-ACCESS  read-only
    STATUS      obsolete
    DESCRIPTION 
        "The latency in responding to gets from the 
         physical server.

	This object is obsolete.It can be measured through lbvserverTable.lbvsvrAvgSvrTTFB."
    ::= { lbStatisticsEntry 10 }

connections OBJECT-TYPE
	SYNTAX Integer32
	MAX-ACCESS read-only
	STATUS obsolete
	DESCRIPTION
		"The number of active connections on the 
		 physical Server.

		This object is obsolete.It can be measured through lbvserverTable.lbvsvrActiveConn."
	::= { lbStatisticsEntry 11 }


lbConfig OBJECT IDENTIFIER
    ::= { loadBalancing 2 }

virServiceTable OBJECT-TYPE
    SYNTAX      SEQUENCE OF VirServiceEntry
    MAX-ACCESS  not-accessible
    STATUS      obsolete
    DESCRIPTION 
        "The table that has all the configuration information 
         for each virtual service.

	This Table is obsolete.Instead of this table use nsVserverGroup.vserverTable.	"
    ::= { lbConfig 1 }

virServiceEntry OBJECT-TYPE
    SYNTAX      VirServiceEntry
    MAX-ACCESS  not-accessible
    STATUS      obsolete
    DESCRIPTION 
        "The Virtual Service Information for each of the entities.

	This Entry is obsolete.Instead of this entry use nsVserverGroup.vserverEntry."
    INDEX       { vserId }
    ::= { virServiceTable 1 }

VirServiceEntry ::= SEQUENCE {
    vserId                Integer32,
    ipAddress           IpAddress,
    port                Integer32,
    vsProtocolType        INTEGER,
    name                OCTET STRING,
    vsLbMethod			INTEGER,
    persistanceType		INTEGER,
    persistanceTimeout  Integer32,
    state				INTEGER
}

vserId OBJECT-TYPE
    SYNTAX      Integer32
    MAX-ACCESS  read-only
    STATUS      obsolete
    DESCRIPTION 
        "The distinguishing Id for each Virtual Service inside
         a NetScaler.

	This object is obsolete."
    ::= { virServiceEntry 1 }

ipAddress OBJECT-TYPE
    SYNTAX      IpAddress
    MAX-ACCESS  read-only
    STATUS      obsolete
    DESCRIPTION 
        "The IP address in the Virtual Service.

	This object is obsolete.It can be measured through vserverTable.vsvrIpAddress.	"
    ::= { virServiceEntry 2 }

port OBJECT-TYPE
    SYNTAX      Integer32
    MAX-ACCESS  read-only
    STATUS      obsolete
    DESCRIPTION 
        "The port in the Virtual Service.

	This object is obsolete.It can be measured through vserverTable.vsvrPort."
    ::= { virServiceEntry 3 }

vsProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type in the Virtual Service.

	This object is obsolete.It can be measured through vserverTable.vsvrType."
    ::= { virServiceEntry 4 }

name OBJECT-TYPE
    SYNTAX      OCTET STRING
    MAX-ACCESS  read-only
    STATUS      obsolete
    DESCRIPTION 
        "The name of the Virtual Service.

	This object is obsolete.It can be measured through vserverTable.vsvrName."
    ::= { virServiceEntry 5 }

vsLbMethod OBJECT-TYPE
	SYNTAX INTEGER	{
		weightedRoundRobin(1), leastConnections(2), leastResponse(3),
		asynchronousMAC(4), urlHashed(5), domainHashed(6),
		destinationIPHashed(7), sourceIPHashed(8), leastBandwidth(9),
		leastPackets(10)
	}
	MAX-ACCESS read-only
	STATUS obsolete
	DESCRIPTION
		"The Policy used for Load Balancing.

		This object is obsolete.It can be measured through lbvserverTable.lbvsvrLBMethod."
	::= { virServiceEntry 6 }

persistanceType OBJECT-TYPE
	SYNTAX INTEGER	{
		sourceIp(1), cookieInsert(2), cookieDelete(3), cookieRead(4),
		cookieHash(5), sessionId(6), server(7)
	}
	MAX-ACCESS read-only
	STATUS obsolete
	DESCRIPTION
		"The type of persistence used.

		This object is obsolete.It can be measured through lbvserverTable.lbvsvrPersistanceType."
	::= {virServiceEntry 7}

persistanceTimeout OBJECT-TYPE
    SYNTAX      Integer32
    MAX-ACCESS  read-only
    STATUS      obsolete
    DESCRIPTION 
        "The timeout set for persistence.

	This object is obsolete.It can be measured through lbvserverTable.lbvsvrPersistanceTimeOut. "
    ::= { virServiceEntry 8 }

state OBJECT-TYPE
	SYNTAX INTEGER	{
		up(0), down(1), unknown(2),
		busy(3), outOfService(4), transitionToOutOfService(5)
	}		
	MAX-ACCESS read-only
	STATUS obsolete
	DESCRIPTION
		"The State of the virtual Service.

		This object is obsolete.It can be measured through vserverTable.vsvrState."
	::= {virServiceEntry 9}


phyServiceTable OBJECT-TYPE
    SYNTAX      SEQUENCE OF PhyServiceEntry
    MAX-ACCESS  not-accessible
    STATUS      obsolete
    DESCRIPTION 
        "The table that has all the configuration information 
         for each physical service.

	This Table is obsolete.Instead of this table use nsSvcGroup.serviceTable."
    ::= { lbConfig 2 }

phyServiceEntry OBJECT-TYPE
    SYNTAX      PhyServiceEntry
    MAX-ACCESS  not-accessible
    STATUS      obsolete
    DESCRIPTION 
        "The Physical Service Information for each of the entities.

	This Entry is obsolete.Instead of this entry use nsSvcGroup.serviceEntry."
    INDEX       { pserId }
    ::= { phyServiceTable 1 }

PhyServiceEntry ::= SEQUENCE {
    pserId            Integer32,
    pserIpAddress     IpAddress,
    pserPort          Integer32,
    psProtocolType    INTEGER,
    psName            OCTET STRING,
    psState			INTEGER,
    weight          Integer32,
    psVsIpAddress     IpAddress,
    psVsPort          Integer32
}

pserId OBJECT-TYPE
    SYNTAX      Integer32
    MAX-ACCESS  read-only
    STATUS      obsolete
    DESCRIPTION 
        "The distinguishing Id for each Physical Service inside
         a NetScaler.

	This object is obsolete."
    ::= { phyServiceEntry 1 }

pserIpAddress OBJECT-TYPE
    SYNTAX      IpAddress
    MAX-ACCESS  read-only
    STATUS      obsolete
    DESCRIPTION 
        "The IP address in the Physical Service.

	This object is obsolete.It can be measured through serviceTable.svcIpAddress."
    ::= { phyServiceEntry 2 }

pserPort OBJECT-TYPE
    SYNTAX      Integer32
    MAX-ACCESS  read-only
    STATUS      obsolete
    DESCRIPTION 
        "The port in the Physical Service.

	This object is obsolete.It can be measured through serviceTable.svcPort."
    ::= { phyServiceEntry 3 }

psProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type in the Physical Service.

	This object is obsolete.It can be measured through serviceTable.svcServiceType."
    ::= { phyServiceEntry 4 }

psName OBJECT-TYPE
    SYNTAX      OCTET STRING
    MAX-ACCESS  read-only
    STATUS      obsolete
    DESCRIPTION 
        "The name of the Physical Service.

	This object is obsolete.It can be measured through serviceTable.svcServiceName."
    ::= { phyServiceEntry 5 }
 
psState OBJECT-TYPE
	SYNTAX INTEGER	{down(0), up(1) }
	MAX-ACCESS read-only
	STATUS obsolete
	DESCRIPTION
		"The state of the Physical Service.

		This object is obsolete.It can be measured through serviceTable.svcState."
	::= {phyServiceEntry 6}

weight OBJECT-TYPE
    SYNTAX      Integer32
    MAX-ACCESS  read-only
    STATUS      obsolete
    DESCRIPTION 
        "The weight assigned to the Physical Service.

	This object is obsolete.It can be measured through vserverServiceTable.serviceWeight."
    ::= { phyServiceEntry 7 }

psVsIpAddress OBJECT-TYPE
    SYNTAX      IpAddress
    MAX-ACCESS  read-only
    STATUS      obsolete
    DESCRIPTION 
        "The IP address in the Virtual Service to which this
         physical service is bound.

	This object is obsolete.It can be measured through vserverTable.vsvrIpAddress."
    ::= { phyServiceEntry 8 }

psVsPort OBJECT-TYPE
    SYNTAX      Integer32
    MAX-ACCESS  read-only
    STATUS      obsolete
    DESCRIPTION 
        "The port in the Virtual Service.

	This object is obsolete.It can be measured through vserverTable.vsvrPort."
    ::= { phyServiceEntry 9 }

sureConnect OBJECT IDENTIFIER
    ::= { nsRoot 4 }

scStatistics OBJECT IDENTIFIER
    ::= { sureConnect 1 }

scperServiceStatisticsTable OBJECT-TYPE
    SYNTAX      SEQUENCE OF ScperServiceStatisticsEntry
    MAX-ACCESS  not-accessible
    STATUS      obsolete
    DESCRIPTION 
        "The Internet On Hold Statistics for each of the entities.

	This Table is obsolete."
    ::= { scStatistics 1 }

scperServiceStatisticsEntry OBJECT-TYPE
    SYNTAX      ScperServiceStatisticsEntry
    MAX-ACCESS  not-accessible
    STATUS      obsolete
    DESCRIPTION 
        "The Internet On Hold Statistics for each of the entities.

	This Entry is obsolete."
    INDEX       { devno }
    ::= { scperServiceStatisticsTable 1 }

ScperServiceStatisticsEntry ::= SEQUENCE {
    devno           Integer32,
    phyIpAddress    IpAddress,
    phyPort         Integer32,
    scProtocolType    INTEGER,
    currentDelay    Integer32,
    avgTxTime       Integer32,
    surgeCount      Integer32,
    iohCount        Integer32
}

devno OBJECT-TYPE
    SYNTAX      Integer32
    MAX-ACCESS  read-only
    STATUS      obsolete
    DESCRIPTION 
        "The distinguishing Id for each physical Service inside
         a NetScaler.

	This object is obsolete."
    ::= { scperServiceStatisticsEntry 1 }

phyIpAddress OBJECT-TYPE
    SYNTAX      IpAddress
    MAX-ACCESS  read-only
    STATUS      obsolete
    DESCRIPTION 
        "The IP address in the Physical Service.

	This object is obsolete.It can be measured through serviceScpolicyTable.svcscpolicyDestIpAddress or vserverScpolicyTable.svcscpolicyDestIpAddress."
    ::= { scperServiceStatisticsEntry 2 }

phyPort OBJECT-TYPE
    SYNTAX      Integer32
    MAX-ACCESS  read-only
    STATUS      obsolete
    DESCRIPTION 
        "The port in the Physical Service.

	This object is obsolete.It can be measured through serviceScpolicyTable.svcscpolicyDestIpPort or vserverScpolicyTable.svcscpolicyDestIpPort."
    ::= { scperServiceStatisticsEntry 3 }

scProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type in the Physical Service.

	This object is obsolete."
    ::= { scperServiceStatisticsEntry 4 }

currentDelay OBJECT-TYPE
    SYNTAX      Integer32
    MAX-ACCESS  read-only
    STATUS      obsolete
    DESCRIPTION 
        "The current Delay on the physical Service.

	This object is obsolete."
    ::= { scperServiceStatisticsEntry 5 }

avgTxTime OBJECT-TYPE
    SYNTAX      Integer32
    MAX-ACCESS  read-only
    STATUS      obsolete
    DESCRIPTION 
        "The average transaction time.

	This object is obsolete.It can be measured through serviceTable.svcAvgSvrTTFB."
    ::= { scperServiceStatisticsEntry 6 }

surgeCount OBJECT-TYPE
    SYNTAX      Integer32
    MAX-ACCESS  read-only
    STATUS      obsolete
    DESCRIPTION 
        "The count of number of times the surge occurred.

	This object is obsolete.It can be measured through serviceTable.svcSurgeCount."
    ::= { scperServiceStatisticsEntry 7 }

iohCount OBJECT-TYPE
    SYNTAX      Integer32
    MAX-ACCESS  read-only
    STATUS      obsolete
    DESCRIPTION 
        "The number of client requests, after having put on hold
         couldnt still access the physical server.

	This object is obsolete."
    ::= { scperServiceStatisticsEntry 8 }

scperPolicyStatisticsTable OBJECT-TYPE
    SYNTAX      SEQUENCE OF ScperPolicyStatisticsEntry
    MAX-ACCESS  not-accessible
    STATUS      obsolete
    DESCRIPTION 
        "The Internet On Hold Statistics for each of the entities.

	This Table is obsolete.Instead of this table use nsSvcGroup.serviceScpolicyTable or nsVserverGroup.vserverScpolicyTable."
    ::= { scStatistics 2 }

scperPolicyStatisticsEntry OBJECT-TYPE
    SYNTAX      ScperPolicyStatisticsEntry
    MAX-ACCESS  not-accessible
    STATUS      obsolete
    DESCRIPTION 
        "The Internet On Hold Statistics for each of the entities.

	This Entry is obsolete.Instead of this entry use nsSvcGroup.serviceScpolicyEntry or nsVserverGroup.vserverScpolicyEntry."
    INDEX       { policydevno }
    ::= { scperPolicyStatisticsTable 1 }

ScperPolicyStatisticsEntry ::= SEQUENCE {
    policydevno             Integer32,
    primaryserviceIp        IpAddress,
    primaryserviceport      Integer32,
    destserviceIp           IpAddress,
    destserviceport         Integer32,
    transactiontime         Integer32,
    totaltransaction        Integer32,
    totalopenconnection     Integer32
}

policydevno OBJECT-TYPE
    SYNTAX      Integer32
    MAX-ACCESS  read-only
    STATUS      obsolete
    DESCRIPTION 
        "The distinguishing Id for each physical Service inside
         a NetScaler.

	This object is obsolete."
    ::= { scperPolicyStatisticsEntry 1 }

primaryserviceIp OBJECT-TYPE
    SYNTAX      IpAddress
    MAX-ACCESS  read-only
    STATUS      obsolete
    DESCRIPTION 
        " ip address of primary service.

	This object is obsolete.It can be measured through serviceScpolicyTable.svcscpolicyPrimaryIPAddress."
    ::= { scperPolicyStatisticsEntry 2 }

primaryserviceport OBJECT-TYPE
    SYNTAX      Integer32
    MAX-ACCESS  read-only
    STATUS      obsolete
    DESCRIPTION 
        " port number of primary service.
	
	This object is obsolete.It can be measured through serviceScpolicyTable.svcscpolicyPrimaryPort or vserverScpolicyTable.vsvrscpolicyPrimaryPort."
    ::= { scperPolicyStatisticsEntry 3 }

destserviceIp OBJECT-TYPE
    SYNTAX      IpAddress
    MAX-ACCESS  read-only
    STATUS      obsolete
    DESCRIPTION 
        " ip address of destination physical service.

	This object is obsolete.It can be measured through serviceScpolicyTable.svcscpolicyDesIpAddress or vserverScpolicyTable.vsvrscpolicyDesIpAddress."
    ::= { scperPolicyStatisticsEntry 4 }

destserviceport OBJECT-TYPE
    SYNTAX      Integer32
    MAX-ACCESS  read-only
    STATUS      obsolete
    DESCRIPTION 
        " port number of destination physical service.

	This object is obsolete.It can be measured through serviceScpolicyTable.svcscpolicyDestPort or vserverScpolicyTable.vsvrscpolicyDestPort."
    ::= { scperPolicyStatisticsEntry 5 }

transactiontime OBJECT-TYPE
    SYNTAX      Integer32
    MAX-ACCESS  read-only
    STATUS      obsolete
    DESCRIPTION 
        " transaction time.

	This object is obsolete.It can be measured through serviceScpolicyTable.svcscpolicyAvgServerTransactionTime or vserverScpolicyTable.vsvrscpolicyAvgServerTransactionTime."
    ::= { scperPolicyStatisticsEntry 6 }

totaltransaction OBJECT-TYPE
    SYNTAX      Integer32
    MAX-ACCESS  read-only
    STATUS      obsolete
    DESCRIPTION 
        " total number of transactions .

	This object is obsolete.It can be measured through serviceScpolicyTable.svcscpolicyTotClientTransaction or vserverScpolicyTable.vsvrscpolicyTotClientTransaction."
    ::= { scperPolicyStatisticsEntry 7 }

totalopenconnection OBJECT-TYPE
    SYNTAX      Integer32
    MAX-ACCESS  read-only
    STATUS      obsolete
    DESCRIPTION 
        " total number of open connections for this policy .

	This object is obsolete.It can be measured through serviceScpolicyTable.svcscpolicyTotOpenConn or vserverScpolicyTable.vsvrscpolicyTotOpenConn."
    ::= { scperPolicyStatisticsEntry 8 }

scGlobalStats OBJECT IDENTIFIER
    ::= { scStatistics 3 }

scUrlHits OBJECT-TYPE
    SYNTAX      Integer32
    MAX-ACCESS  read-only
    STATUS      obsolete
    DESCRIPTION 
        "this Counter gives the  number of times we matched an
         incoming request with a Configured sureconnect  policy .

	This object is obsolete.It can be measured through scPolicyStatistics.scPolicyUrlHits."
    ::= { scGlobalStats 1 }

popUps OBJECT-TYPE
	SYNTAX Integer32
	MAX-ACCESS read-only
	STATUS obsolete
	DESCRIPTION
		"this Counter gives the number of times  we served the
		in-memory java script which throws up the pop up window.

		This object is obsolete.It can be measured through scPolicyStatistics.scPopUps."
	::= { scGlobalStats 2 }

altContUrls OBJECT-TYPE
	SYNTAX Integer32
	MAX-ACCESS read-only
	STATUS obsolete
	DESCRIPTION
		"this Counter gives the total  number of requests which
		came with the onhold cookie. So, this gives the number requests
 		which  are required to load the alternate content in the pop up
 		window.

		This object is obsolete.It can be measured through scPolicyStatistics.scAltContUrls."

	::= { scGlobalStats 3 }

sessReqs OBJECT-TYPE
	SYNTAX Integer32
	MAX-ACCESS read-only
	STATUS	obsolete
	DESCRIPTION
		"this Counter gives the number requests which came in a
		SureConnect session. 

		This object is obsolete.It can be measured through scPolicyStatistics.scSessionReqs."
	::= {scGlobalStats 4 }

postReqs OBJECT-TYPE
	SYNTAX Integer32
	MAX-ACCESS read-only
	STATUS obsolete
	DESCRIPTION
		"this Counter gives the number of times a post request
		triggered  SureConnect.

		This object is obsolete.It can be measured through scPolicyStatistics.scPostReqs."
	::= { scGlobalStats 5 }

thresholdFail OBJECT-TYPE
	SYNTAX Integer32
	MAX-ACCESS read-only
	STATUS obsolete
	DESCRIPTION
		" this Counter gives the number of times we did not serve the
		in-memory response because  the  thresholds conditions had failed.

		This object is obsolete.It can be measured through scPolicyStatistics.scThresholdFail. "
	::= { scGlobalStats 6}

faultyCookies OBJECT-TYPE
	SYNTAX Integer32
	MAX-ACCESS read-only
	STATUS obsolete
	DESCRIPTION
		"this Counter gives the number of times we encountered
		corrupted SureConnect Cookies.

	This object is obsolete.It can be measured through scPolicyStatistics.scFaultyCookies."
	::= { scGlobalStats 7}

unSupBrow OBJECT-TYPE
	SYNTAX Integer32
	MAX-ACCESS read-only
	STATUS obsolete
	DESCRIPTION
		"this Counter gives the number of times requests came from
		unsupported browsers. For a list of  browsers supported by
		SureConnect, please check the Functional Spec.

	This object is obsolete.It can be measured through scPolicyStatistics.scUnSupBrow."
	::= { scGlobalStats 8}

resetStats OBJECT-TYPE
	SYNTAX Integer32
	MAX-ACCESS read-only
	STATUS obsolete
	DESCRIPTION
		"This gives the number of times delay stats were reset.
		Delay stats are reset when there is no traffic to the configured
		url for more than 10 minutes.

	This object is obsolete.It can be measured through scPolicyStatistics.scResetStats."
	::= { scGlobalStats 9}		

scConfig OBJECT IDENTIFIER
    ::= { sureConnect 2 }

scPolicyconfigTable OBJECT-TYPE
    SYNTAX      SEQUENCE OF ScPolicyconfigEntry
    MAX-ACCESS  not-accessible
    STATUS      obsolete
    DESCRIPTION 
        "The Internet On Hold Statistics for each of the entities.

	This Table is obsolete.Instead of this table use nsScPolicyGroup.scPolicyConfigTable.	"
    ::= { scConfig 1 }

scPolicyconfigEntry OBJECT-TYPE
    SYNTAX      ScPolicyconfigEntry
    MAX-ACCESS  not-accessible
    STATUS      obsolete
    DESCRIPTION 
        "The Internet On Hold Statistics for each of the entities.

	This Entry is obsolete.Instead of this entry use nsScPolicyGroup.scPolicyConfigEntry."
    INDEX       { policyIndex }
    ::= { scPolicyconfigTable 1 }

ScPolicyconfigEntry ::= SEQUENCE {
    policyIndex                     Integer32,
    policyName                      OCTET STRING,
    scPolicyUrl                     OCTET STRING,
    delayThreshold                  INTEGER,
    maxConnections                  INTEGER,
    actionType						INTEGER,
    alternatecontentServicename     OCTET STRING,
    ruleName                        OCTET STRING,
    alternatecontentPath            OCTET STRING
}

policyIndex OBJECT-TYPE
    SYNTAX      Integer32
    MAX-ACCESS  read-only
    STATUS      obsolete
    DESCRIPTION 
        "The distinguishing Id for each On Hold Policy inside
         a NetScaler.

	This object is obsolete."
    ::= { scPolicyconfigEntry 1 }

policyName OBJECT-TYPE
    SYNTAX      OCTET STRING
    MAX-ACCESS  read-only
    STATUS      obsolete
    DESCRIPTION 
        "The name of the Physical Service.

	This object is obsolete.It can be measured through scPolicyConfigTable.scPolicyName."
    ::= { scPolicyconfigEntry 2 }

scPolicyUrl OBJECT-TYPE
    SYNTAX      OCTET STRING
    MAX-ACCESS  read-only
    STATUS      obsolete
    DESCRIPTION 
        "The URL in the IOH Policy.
		
	This object is obsolete.It can be measured through scPolicyConfigTable.scPolUrl."
    ::= { scPolicyconfigEntry 3 }

delayThreshold OBJECT-TYPE
    SYNTAX      INTEGER { notconfigured(-1) }
    MAX-ACCESS  read-only
    STATUS      obsolete
    DESCRIPTION 
        "The delay threshold.

	This object is obsolete.It can be measured through scPolicyConfigTable.scDelayThreshold."
    ::= { scPolicyconfigEntry 4 }

maxConnections OBJECT-TYPE
    SYNTAX      INTEGER { notconfigured(-1) }
    MAX-ACCESS  read-only
    STATUS      obsolete
    DESCRIPTION 
        "The max connections.

	This object is obsolete.It can be measured through scPolicyConfigTable.scMaxConnections."
    ::= { scPolicyconfigEntry 5 }

actionType OBJECT-TYPE
	SYNTAX INTEGER { ns (0), acs (1), noAction(4) }
	MAX-ACCESS read-only
	STATUS obsolete
	DESCRIPTION
		"The type of action that NetScaler takes when initiating on-hold.

	This object is obsolete.It can be measured through scPolicyConfigTable.scActionType."
	::= { scPolicyconfigEntry 6}
		
alternatecontentServicename OBJECT-TYPE
    SYNTAX      OCTET STRING
    MAX-ACCESS  read-only
    STATUS      obsolete
    DESCRIPTION 
        "The alternate service name for the content.

	This object is obsolete.It can be measured through scPolicyConfigTable.scAlternateContentServiceName. "
    ::= { scPolicyconfigEntry 7 }

ruleName OBJECT-TYPE
    SYNTAX      OCTET STRING
    MAX-ACCESS  read-only
    STATUS      obsolete
    DESCRIPTION 
        " Rule Name .

	This object is obsolete.It can be measured through scPolicyConfigTable.scRuleName."
    ::= { scPolicyconfigEntry 8 }

alternatecontentPath OBJECT-TYPE
    SYNTAX      OCTET STRING
    MAX-ACCESS  read-only
    STATUS      obsolete
    DESCRIPTION 
        "The alternate path for the content.

	This object is obsolete.It can be measured through scPolicyConfigTable.scAlternateContentPath. "
    ::= { scPolicyconfigEntry 9 }

contentSwitching OBJECT IDENTIFIER
    ::= { nsRoot 5 }

cswStatisticsTable OBJECT-TYPE
    SYNTAX      SEQUENCE OF CswStatisticsEntry
    MAX-ACCESS  not-accessible
    STATUS      obsolete
    DESCRIPTION 
        "The Content Switching Statistics for each of the entities.

	This Table is obsolete.Instead of this table use nsVserverGroup.vserverTable."
    ::= { contentSwitching 1 }

cswStatisticsEntry OBJECT-TYPE
    SYNTAX      CswStatisticsEntry
    MAX-ACCESS  not-accessible
    STATUS      obsolete
    DESCRIPTION 
        "The Content Switching Statistics for each of the entities.

	This Entry is obsolete.Instead of this entry use nsVserverGroup.vserverEntry."
    INDEX       { cswIndex }
    ::= { cswStatisticsTable 1 }

CswStatisticsEntry ::= SEQUENCE {
    cswIndex           Integer32,
    cswVsIpAddress     IpAddress,
    cswVsPort          Integer32,
    cswProtocolType    INTEGER,
    virServiceName  OCTET STRING,
    vsHits          Integer32,
    vsMiss          Integer32
}

cswIndex OBJECT-TYPE
    SYNTAX      Integer32
    MAX-ACCESS  read-only
    STATUS      obsolete
    DESCRIPTION 
        "The distinguishing Id for each virtual Service inside
         a NetScaler.

	This object is obsolete."
    ::= { cswStatisticsEntry 1 }

cswVsIpAddress OBJECT-TYPE
    SYNTAX      IpAddress
    MAX-ACCESS  read-only
    STATUS      obsolete
    DESCRIPTION 
        "The IP address in the Virtual Service.

	This object is obsolete.It can be measured through vserverTable.vsvrIpAddress."
    ::= { cswStatisticsEntry 2 }

cswVsPort OBJECT-TYPE
    SYNTAX      Integer32
    MAX-ACCESS  read-only
    STATUS      obsolete
    DESCRIPTION 
        "The port in the Virtual Service.

	This object is obsolete.It can be measured through vserverTable.vsvrPort."
    ::= { cswStatisticsEntry 3 }

cswProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type of the Virtual Server.

	This object is obsolete.It can be measured through vserverTable.vsvrType."
    ::= { cswStatisticsEntry 4 }

virServiceName OBJECT-TYPE
    SYNTAX      OCTET STRING
    MAX-ACCESS  read-only
    STATUS      obsolete
    DESCRIPTION 
        "The name of the CSW Virtual server.

	This object is obsolete.It can be measured through vserverTable.vsvrName. "
    ::= { cswStatisticsEntry 5 }

vsHits OBJECT-TYPE
    SYNTAX      Integer32
    MAX-ACCESS  read-only
    STATUS      obsolete
    DESCRIPTION 
        "The total hits on all the policies bound to this virtual server.

	This object is obsolete.It can be measured through vserverTable.vsvrTotalRequests."
    ::= { cswStatisticsEntry 6 }

vsMiss OBJECT-TYPE
    SYNTAX      Integer32
    MAX-ACCESS  read-only
    STATUS      obsolete
    DESCRIPTION 
        "The total Miss on all the policies bound to this virtual server.

	This object is obsolete.It can be measured through vserverTable.vsvrTotalMiss."
    ::= { cswStatisticsEntry 7 }

cswConfigTable OBJECT-TYPE
    SYNTAX      SEQUENCE OF CswConfigEntry
    MAX-ACCESS  not-accessible
    STATUS      obsolete
    DESCRIPTION 
        "The CSW configuration information for each of the entities.

	This Table is obsolete.Instead of this table use nsVserverGroup.vserverCspolicyTable."
    ::= { contentSwitching 2 }

cswConfigEntry OBJECT-TYPE
    SYNTAX      CswConfigEntry
    MAX-ACCESS  not-accessible
    STATUS      obsolete
    DESCRIPTION 
        "The CSW configuration information for each of the entities.

	This Entry is obsolete.Instead of this entry use nsVserverGroup.vserverCspolicyEntry."
    INDEX       { cswVsId, policyId }
    ::= { cswConfigTable 1 }

CswConfigEntry ::= SEQUENCE {
    cswVsId            Integer32,
    policyId        Integer32,
    vServerName     OCTET STRING,
    policyname      OCTET STRING,
    policyvalue     OCTET STRING,
    policyHits      Integer32,
    domain          OCTET STRING
}

cswVsId OBJECT-TYPE
    SYNTAX      Integer32
    MAX-ACCESS  read-only
    STATUS      obsolete
    DESCRIPTION 
        "The distinguishing Id for each CSW Vserver inside
         a NetScaler.

	This object is obsolete."
    ::= { cswConfigEntry 1 }

policyId OBJECT-TYPE
    SYNTAX      Integer32
    MAX-ACCESS  read-only
    STATUS      obsolete
    DESCRIPTION 
        "The distinguishing Id for each CSW Policy inside
         a NetScaler.

	This object is obsolete."
    ::= { cswConfigEntry 2 }

vServerName OBJECT-TYPE
    SYNTAX      OCTET STRING
    MAX-ACCESS  read-only
    STATUS      obsolete
    DESCRIPTION 
        "The name of the CSW Virtual Server.

	This object is obsolete."
    ::= { cswConfigEntry 3 }

policyname OBJECT-TYPE
    SYNTAX      OCTET STRING
    MAX-ACCESS  read-only
    STATUS      obsolete
    DESCRIPTION 
        "The name of the policy binding to a Virtual Server.

	This object is obsolete.It can be measured through vserverCspolicyTable.cspolicyName."
    ::= { cswConfigEntry 4 }

policyvalue OBJECT-TYPE
    SYNTAX      OCTET STRING
    MAX-ACCESS  read-only
    STATUS      obsolete
    DESCRIPTION 
        "The value of the policy.

	 This object is obsolete."
    ::= { cswConfigEntry 5 }

policyHits OBJECT-TYPE
    SYNTAX      Integer32
    MAX-ACCESS  read-only
    STATUS      obsolete
    DESCRIPTION 
        "The hits on the Policy in the Virtual Service.

	This object is obsolete.It can be measured through vserverCspolicyTable.cspolicyHits."
    ::= { cswConfigEntry 6 }

domain OBJECT-TYPE
    SYNTAX      OCTET STRING
    MAX-ACCESS  read-only
    STATUS      obsolete
    DESCRIPTION 
        "The domain hosted by the CSW vserver.

	This object is obsolete."
    ::= { cswConfigEntry 7 }

cacheRedirection OBJECT IDENTIFIER
    ::= { nsRoot 6 }

crStatisticsTable OBJECT-TYPE
    SYNTAX      SEQUENCE OF CrStatisticsEntry
    MAX-ACCESS  not-accessible
    STATUS      obsolete
    DESCRIPTION 
        "The Cache Redirection Statistics for each of the entities.

	This Table is obsolete.Instead of this table use nsVserverGroup.vserverTable."
    ::= { cacheRedirection 1 }

crStatisticsEntry OBJECT-TYPE
    SYNTAX      CrStatisticsEntry
    MAX-ACCESS  not-accessible
    STATUS      obsolete
    DESCRIPTION 
        "The Cache Redirection Statistics for each of the entities.

	This Entry is obsolete.Instead of this entry use nsVserverGroup.vserverEntry."
    INDEX       { crVsIndex }
    ::= { crStatisticsTable 1 }

CrStatisticsEntry ::= SEQUENCE {
    crVsIndex           Integer32,
    crVsIpAddress     IpAddress,
    crVsPort          Integer32,
    crProtocolType    INTEGER,
    crVirServiceName  OCTET STRING,
    crVsHits          Integer32,
    crVsMiss          Integer32
}

crVsIndex OBJECT-TYPE
    SYNTAX      Integer32
    MAX-ACCESS  read-only
    STATUS      obsolete
    DESCRIPTION 
        "The distinguishing Id for each virtual Service inside
         a NetScaler.

	This object is obsolete."
    ::= { crStatisticsEntry 1 }

crVsIpAddress OBJECT-TYPE
    SYNTAX      IpAddress
    MAX-ACCESS  read-only
    STATUS      obsolete
    DESCRIPTION 
        "The IP address in the Virtual Service.

	This object is obsolete.It can be measured through vserverTable.vsvrIpAddress."
    ::= { crStatisticsEntry 2 }

crVsPort OBJECT-TYPE
    SYNTAX      Integer32
    MAX-ACCESS  read-only
    STATUS      obsolete
    DESCRIPTION 
        "The port in the Virtual Service.

	This object is obsolete.It can be measured through vserverTable.vsvrPort."
    ::= { crStatisticsEntry 3 }

crProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      obsolete
    DESCRIPTION 
        "The protocol type in the Physical Service.

	This object is obsolete.It can be measured through vserverTable.vsvrType."
    ::= { crStatisticsEntry 4 }

crVirServiceName OBJECT-TYPE
    SYNTAX      OCTET STRING
    MAX-ACCESS  read-only
    STATUS      obsolete
    DESCRIPTION 
        "The name of the CSW Virtual server.

	This object is obsolete.It can be measured through vserverTable.vsvrName. "
    ::= { crStatisticsEntry 5 }

crVsHits OBJECT-TYPE
    SYNTAX      Integer32
    MAX-ACCESS  read-only
    STATUS      obsolete
    DESCRIPTION 
        "The total hits on the policies.

	This object is obsolete.It can be measured through vserverTable.vsvrTotalRequests."
    ::= { crStatisticsEntry 6 }

crVsMiss OBJECT-TYPE
    SYNTAX      Integer32
    MAX-ACCESS  read-only
    STATUS      obsolete
    DESCRIPTION 
        "The total Miss on the policy.

	This object is obsolete.It can be measured through vserverTable.vsvrTotMiss."
    ::= { crStatisticsEntry 7 }

crConfig OBJECT IDENTIFIER
    ::= { cacheRedirection 2 }

crPolBindConfigTable OBJECT-TYPE
    SYNTAX      SEQUENCE OF CrPolBindConfigEntry
    MAX-ACCESS  not-accessible
    STATUS      obsolete
    DESCRIPTION 
        "The CR policy binding configuration information for each of the entry.

	This Table is obsolete.Instead of this table use nsVserverGroup.vserverCrpolicyTable."
    ::= { crConfig 1 }

crPolBindConfigEntry OBJECT-TYPE
    SYNTAX      CrPolBindConfigEntry
    MAX-ACCESS  not-accessible
    STATUS      obsolete
    DESCRIPTION 
        "The CR policy binding configuration information for each of the entry.

	This Entry is obsolete.Instead of this entry use nsVserverGroup.vserverCrpolicyEntry."
    INDEX       { bindId }
    ::= { crPolBindConfigTable 1 }

CrPolBindConfigEntry ::= SEQUENCE {
    bindId          Integer32,
    crbVServerName     OCTET STRING,
    crbPolicyname      OCTET STRING,
    crbPolicyvalue     OCTET STRING,
    crbPolicyHits      Integer32
}

bindId OBJECT-TYPE
    SYNTAX      Integer32
    MAX-ACCESS  read-only
    STATUS      obsolete
    DESCRIPTION 
        "The unique binding Id for each CR Policy inside
         a NetScaler.

	This object is obsolete."
    ::= { crPolBindConfigEntry 1 }

crbVServerName OBJECT-TYPE
    SYNTAX      OCTET STRING
    MAX-ACCESS  read-only
    STATUS      obsolete
    DESCRIPTION 
        "The name of the CR Virtual Server.

	This object is obsolete."
    ::= { crPolBindConfigEntry 2 }

crbPolicyname OBJECT-TYPE
    SYNTAX      OCTET STRING
    MAX-ACCESS  read-only
    STATUS      obsolete
    DESCRIPTION 
        "The name of the policy binding to a Virtual Server.

	This object is obsolete.It can be measured through vserverCrpolicyTable.crpolicyName."
    ::= { crPolBindConfigEntry 3 }

crbPolicyvalue OBJECT-TYPE
    SYNTAX      OCTET STRING
    MAX-ACCESS  read-only
    STATUS      obsolete
    DESCRIPTION 
        "The value of the policy.

	This object is obsolete."
    ::= { crPolBindConfigEntry 4 }

crbPolicyHits OBJECT-TYPE
    SYNTAX      Integer32
    MAX-ACCESS  read-only
    STATUS      obsolete
    DESCRIPTION 
        "The hits on the Policy in the Virtual Service.

	This object is obsolete.It can be measured through vserverCrpolicyTable.crpolicyHits."
    ::= { crPolBindConfigEntry 5 }

crMapBindConfigTable OBJECT-TYPE
    SYNTAX      SEQUENCE OF CrMapBindConfigEntry
    MAX-ACCESS  not-accessible
    STATUS      obsolete
    DESCRIPTION 
        "The CR map policy binding configuration information for each of the entry.

	This Table is obsolete."
    ::= { crConfig 2 }

crMapBindConfigEntry OBJECT-TYPE
    SYNTAX      CrMapBindConfigEntry
    MAX-ACCESS  not-accessible
    STATUS      obsolete
    DESCRIPTION 
        "The CR map policy binding configuration information for each of the entry.

	This Entry is obsolete."
    INDEX       { mapbindId }
    ::= { crMapBindConfigTable 1 }

CrMapBindConfigEntry ::= SEQUENCE {
    mapbindId       Integer32,
    mapName         OCTET STRING,
    mapHits         Integer32,
    vserverName     OCTET STRING
}

mapbindId OBJECT-TYPE
    SYNTAX      Integer32
    MAX-ACCESS  read-only
    STATUS      obsolete
    DESCRIPTION 
        "The unique binding Id for each CR Map Policy inside
         a NetScaler.

	This object is obsolete."
    ::= { crMapBindConfigEntry 1 }

mapName OBJECT-TYPE
    SYNTAX      OCTET STRING
    MAX-ACCESS  read-only
    STATUS      obsolete
    DESCRIPTION 
        "The name of the map policy bound to CR Virtual Server.

	This object is obsolete."
    ::= { crMapBindConfigEntry 2 }

mapHits OBJECT-TYPE
    SYNTAX      Integer32
    MAX-ACCESS  read-only
    STATUS      obsolete
    DESCRIPTION 
        "The hits on the Map Policy in the Virtual Service.

	This object is obsolete."
    ::= { crMapBindConfigEntry 3 }

vserverName OBJECT-TYPE
    SYNTAX      OCTET STRING
    MAX-ACCESS  read-only
    STATUS      obsolete
    DESCRIPTION 
        "The name of the CR vserver.

	This object is obsolete."
    ::= { crMapBindConfigEntry 4 }

crMapConfigTable OBJECT-TYPE
    SYNTAX      SEQUENCE OF CrMapConfigEntry
    MAX-ACCESS  not-accessible
    STATUS      obsolete
    DESCRIPTION 
        "The CR map configuration information for each of the entry.

	This Table is obsolete.Instead of this table use nsSysGroup.crConfigGroup.crPolicyMapConfigTable."
    ::= { crConfig 3 }

crMapConfigEntry OBJECT-TYPE
    SYNTAX      CrMapConfigEntry
    MAX-ACCESS  not-accessible
    STATUS      obsolete
    DESCRIPTION 
        "The CR map configuration information for each of the entry.

	This Entry is obsolete.Instead of this entry use nsSysGroup.crConfigGroup.crPolicyMapConfigEntry."
    INDEX       { crmIndex }
    ::= { crMapConfigTable 1 }

CrMapConfigEntry ::= SEQUENCE {
    crmIndex       Integer32,
    crmMapName     OCTET STRING,
    srcDomain   OCTET STRING,
    dstDomain   OCTET STRING,
    srcUrl      OCTET STRING,
    dstUrl      OCTET STRING
}

crmIndex OBJECT-TYPE
    SYNTAX      Integer32
    MAX-ACCESS  read-only
    STATUS      obsolete
    DESCRIPTION 
        "The unique Id for each CR Map inside
         a NetScaler.

	This object is obsolete."
    ::= { crMapConfigEntry 1 }

crmMapName OBJECT-TYPE
    SYNTAX      OCTET STRING
    MAX-ACCESS  read-only
    STATUS      obsolete
    DESCRIPTION 
        "The name of the map policy.

	This object is obsolete.It can be measured through crPolicyMapConfigTable.crMapName."
    ::= { crMapConfigEntry 2 }

srcDomain OBJECT-TYPE
    SYNTAX      OCTET STRING
    MAX-ACCESS  read-only
    STATUS      obsolete
    DESCRIPTION 
        "The name of the source domain hosted by the map.

	This object is obsolete.It can be measured through crPolicyMapConfigTable.crMapSrcName."
    ::= { crMapConfigEntry 3 }

dstDomain OBJECT-TYPE
    SYNTAX      OCTET STRING
    MAX-ACCESS  read-only
    STATUS      obsolete
    DESCRIPTION 
        "The name of the destination domain after the mapping is applied.

	This object is obsolete.It can be measured through crPolicyMapConfigTable.crMapDstName."
    ::= { crMapConfigEntry 4 }

srcUrl OBJECT-TYPE
    SYNTAX      OCTET STRING
    MAX-ACCESS  read-only
    STATUS      obsolete
    DESCRIPTION 
        "The Url to be modified under the given source domain.

	This object is obsolete.It can be measured through crPolicyMapConfigTable.crMapSrcUrl."
    ::= { crMapConfigEntry 5 }

dstUrl OBJECT-TYPE
    SYNTAX      OCTET STRING
    MAX-ACCESS  read-only
    STATUS      obsolete
    DESCRIPTION 
        "The Url after mapping.

	This object is obsolete.It can be measured through crPolicyMapConfigTable.crMapDstUrl."
    ::= { crMapConfigEntry 6 }

compression OBJECT IDENTIFIER
    ::= { nsRoot 7 }

compressionStats OBJECT IDENTIFIER
    ::= { compression 1 }

cmpTotRequests OBJECT-TYPE
    SYNTAX      Counter32
    MAX-ACCESS  read-only
    STATUS      obsolete
    DESCRIPTION 
        " Number of compression requests done"
    ::= { compressionStats 1 }

cmpTotTxbytes OBJECT-TYPE
    SYNTAX      Counter32
    MAX-ACCESS  read-only
    STATUS      obsolete
    DESCRIPTION 
        " Number of compressed bytes transmitted"
    ::= { compressionStats 2 }

cmpTotRxbytes OBJECT-TYPE
    SYNTAX      Counter32
    MAX-ACCESS  read-only
    STATUS      obsolete
    DESCRIPTION 
        " Number of compressible bytes received"
    ::= { compressionStats 3 }

cmpTotTxpkts OBJECT-TYPE
    SYNTAX      Counter32
    MAX-ACCESS  read-only
    STATUS      obsolete
    DESCRIPTION 
        " Number of compressed packets transmitted"
    ::= { compressionStats 4 }

cmpTotRxpkts OBJECT-TYPE
    SYNTAX      Counter32
    MAX-ACCESS  read-only
    STATUS      obsolete
    DESCRIPTION 
        " Number of compressible packets received"
    ::= { compressionStats 5 }

compressionRatio OBJECT-TYPE
    SYNTAX      OCTET STRING
    MAX-ACCESS  read-only
    STATUS      obsolete
    DESCRIPTION 
        " ratio of compressible data received vs compressed data transmitted"
    ::= { compressionStats 6 }

totalDataCompressionRatio OBJECT-TYPE
    SYNTAX      OCTET STRING
    MAX-ACCESS  read-only
    STATUS      obsolete
    DESCRIPTION 
        " ratio of total data received to total data transmitted"
    ::= { compressionStats 7 }

vlan OBJECT IDENTIFIER
    ::= { nsRoot 8 }

vlanstatsTable OBJECT-TYPE
    SYNTAX      SEQUENCE OF VlanstatsEntry
    MAX-ACCESS  not-accessible
    STATUS      obsolete
    DESCRIPTION 
        "The Vlan Statistics for each of the entities."
    ::= { vlan 1 }

vlanstatsEntry OBJECT-TYPE
    SYNTAX      VlanstatsEntry
    MAX-ACCESS  not-accessible
    STATUS      obsolete
    DESCRIPTION 
        "The Vlan Statistics for each of the entities."
    INDEX       { vlansDevno }
    ::= { vlanstatsTable 1 }

VlanstatsEntry ::= SEQUENCE {
    vlansDevno                   Integer32,
    totalrxpkts             Counter32,
    totaltxpkts             Counter32,
    totalrxbytes            Counter32,
    totaltxbytes            Counter32,
    totaldroppedpkts        Counter32,
    totalbroadcastpackets   Counter32
}

vlansDevno OBJECT-TYPE
    SYNTAX      Integer32
    MAX-ACCESS  read-only
    STATUS      obsolete
    DESCRIPTION 
        "The distinguishing Id for each vlan inside
         netscaler"
    ::= { vlanstatsEntry 1 }

totalrxpkts OBJECT-TYPE
    SYNTAX      Counter32
    MAX-ACCESS  read-only
    STATUS      obsolete
    DESCRIPTION 
        "Total Number of packets received in this vlan "
    ::= { vlanstatsEntry 2 }

totaltxpkts OBJECT-TYPE
    SYNTAX      Counter32
    MAX-ACCESS  read-only
    STATUS      obsolete
    DESCRIPTION 
        "Total Number of packets transmitted in this vlan"
    ::= { vlanstatsEntry 3 }

totalrxbytes OBJECT-TYPE
    SYNTAX      Counter32
    MAX-ACCESS  read-only
    STATUS      obsolete
    DESCRIPTION 
        "Total Number of bytes received in this vlan "
    ::= { vlanstatsEntry 4 }

totaltxbytes OBJECT-TYPE
    SYNTAX      Counter32
    MAX-ACCESS  read-only
    STATUS      obsolete
    DESCRIPTION 
        "Total Number of bytes transmitted in this vlan"
    ::= { vlanstatsEntry 5 }

totaldroppedpkts OBJECT-TYPE
    SYNTAX      Counter32
    MAX-ACCESS  read-only
    STATUS      obsolete
    DESCRIPTION 
        "Total Number of dropped packets in this vlan"
    ::= { vlanstatsEntry 6 }

totalbroadcastpackets OBJECT-TYPE
    SYNTAX      Counter32
    MAX-ACCESS  read-only
    STATUS      obsolete
    DESCRIPTION 
        "Total Number of broadcasted packets in this vlan"
    ::= { vlanstatsEntry 7 }

vlanconfigTable OBJECT-TYPE
    SYNTAX      SEQUENCE OF VlanconfigEntry
    MAX-ACCESS  not-accessible
    STATUS      obsolete
    DESCRIPTION 
        "The Vlan config Statistics for each of the entities.

	This Table is obsolete.Instead of this table use nsSysGroup.vlanTable."
    ::= { vlan 2 }

vlanconfigEntry OBJECT-TYPE
    SYNTAX      VlanconfigEntry
    MAX-ACCESS  not-accessible
    STATUS      obsolete
    DESCRIPTION 
        "The Vlan config Statistics for each of the entities.

	This Entry is obsolete.Instead of this entry use nsSysGroup.vlanEntry."
    INDEX       { vlancDevno }
    ::= { vlanconfigTable 1 }

VlanconfigEntry ::= SEQUENCE {
    vlancDevno       Integer32,
    tagId       Integer32,
    vlancInterfaces  OCTET STRING,
    ipaddress   IpAddress,
    netmask     IpAddress,
    tagging     OCTET STRING
}

vlancDevno OBJECT-TYPE
    SYNTAX      Integer32
    MAX-ACCESS  read-only
    STATUS      obsolete
    DESCRIPTION 
        "The distinguishing Id for each vlan inside
         netscaler.

	This object is obsolete."
    ::= { vlanconfigEntry 1 }

tagId OBJECT-TYPE
    SYNTAX      Integer32
    MAX-ACCESS  read-only
    STATUS      obsolete
    DESCRIPTION 
        "The unique tag Id for each vlan inside
         NetScaler.

	This object is obsolete.It can be measured through vlanTable.vlanId."
    ::= { vlanconfigEntry 2 }

vlancInterfaces OBJECT-TYPE
    SYNTAX      OCTET STRING
    MAX-ACCESS  read-only
    STATUS      obsolete
    DESCRIPTION 
        "The port number associated to each vlan inside
         netscaler.
	
	This object is obsolete.It can be measured through vlanTable.vlanMemberInterfaces."
    ::= { vlanconfigEntry 3 }

ipaddress OBJECT-TYPE
    SYNTAX      IpAddress
    MAX-ACCESS  read-only
    STATUS      obsolete
    DESCRIPTION 
        "The ipaddress for each vlan inside
         netscaler.

	This object is obsolete.It can be measured through vlanTable.vlanBindIpAddress."
    ::= { vlanconfigEntry 4 }

netmask OBJECT-TYPE
    SYNTAX      IpAddress
    MAX-ACCESS  read-only
    STATUS      obsolete
    DESCRIPTION 
        "The netmask corresponding to ipaddress for each vlan inside
         netscaler.

	This object is obsolete.It can be measured through vlanTable.vlanBindIpNetmask."
    ::= { vlanconfigEntry 5 }

tagging OBJECT-TYPE
    SYNTAX      OCTET STRING
    MAX-ACCESS  read-only
    STATUS      obsolete
    DESCRIPTION 
        "Tagged member interfaces of this vlan.

	This object is obsolete."
    ::= { vlanconfigEntry 6 }

domainNameService OBJECT IDENTIFIER
    ::= { nsRoot 9 }

dnsServer OBJECT IDENTIFIER
    ::= { domainNameService 1 }

dnsServerStatistics OBJECT IDENTIFIER
    ::= { dnsServer 1 }

totQueries OBJECT-TYPE
    SYNTAX      Counter32
    MAX-ACCESS  read-only
    STATUS      obsolete
    DESCRIPTION 
        "this Counter gives the  number of times NetScaler as a 
         name server received a query for any kind of DNS Record.

	This object is obsolete.It can be measured through nsDomainServiceName.dnsTotQueries.  "
    ::= { dnsServerStatistics 1 }

totAnswers OBJECT-TYPE
    SYNTAX      Counter32
    MAX-ACCESS  read-only
    STATUS      obsolete
    DESCRIPTION 
        "this Counter gives the  number of times NetScaler as a 
         name server received a query for a name server Record.

	This object is obsolete.It can be measured through nsDomainServiceName.dnsTotAnswers. "
    ::= { dnsServerStatistics 2 }

totAuthAns OBJECT-TYPE
    SYNTAX      Counter32
    MAX-ACCESS  read-only
    STATUS      obsolete
    DESCRIPTION 
        "Number of queries which were authoritatively answered.

	This object is obsolete.It can be measured through nsDomainServiceName.dnsTotAuthAns."
    ::= { dnsServerStatistics 3 }

totAuthNoNames OBJECT-TYPE
    SYNTAX      Counter32
    MAX-ACCESS  read-only
    STATUS      obsolete
    DESCRIPTION 
        "Number of queries for which `authoritative no such name'
         responses were made.

	This object is obsolete.It can be measured through nsDomainServiceName.dnsTotAuthNoNames."
    ::= { dnsServerStatistics 4 }

totAuthNoDataResps OBJECT-TYPE
    SYNTAX      Counter32
    MAX-ACCESS  read-only
    STATUS      obsolete
    DESCRIPTION 
        "Number of queries for which `authoritative no such data'
         (empty answer) responses were made.

	This object is obsolete.It can be measured through nsDomainServiceName.dnsTotAuthNoDataResps."
    ::= { dnsServerStatistics 5 }

totNonAuthDatas OBJECT-TYPE
    SYNTAX      Counter32
    MAX-ACCESS  read-only
    STATUS      obsolete
    DESCRIPTION 
        "Number of queries which were non-authoritatively
         answered (cached data).

	 This object is obsolete.It can be measured through nsDomainServiceName.dnsTotStrayAnswer."
    ::= { dnsServerStatistics 6 }

totNonAuthNoDatas OBJECT-TYPE
    SYNTAX      Counter32
    MAX-ACCESS  read-only
    STATUS      obsolete
    DESCRIPTION 
        "Number of queries which were non-authoritatively
         answered with no data (empty answer).

	This object is obsolete.It can be measured through nsDomainServiceName.dnsTotNonAuthNoDatas."
    ::= { dnsServerStatistics 7 }

totReqRefusals OBJECT-TYPE
    SYNTAX      Counter32
    MAX-ACCESS  read-only
    STATUS      obsolete
    DESCRIPTION 
        "Number of DNS requests refused by the server.

	This object is obsolete.It can be measured through nsDomainServiceName.dnsTotReqRefusals."
    ::= { dnsServerStatistics 8 }

totReqUnparses OBJECT-TYPE
    SYNTAX      Counter32
    MAX-ACCESS  read-only
    STATUS      obsolete
    DESCRIPTION 
        "Number of requests received which were unparseable.

	This object is obsolete."
    ::= { dnsServerStatistics 9 }

totOtherErrors OBJECT-TYPE
    SYNTAX      Counter32
    MAX-ACCESS  read-only
    STATUS      obsolete
    DESCRIPTION 
        "Number of requests which were aborted for other (local)
         server errors.

	This object is obsolete.It can be measured through nsDomainServiceName.dnsTotOtherErrors."
    ::= { dnsServerStatistics 10 }

aRecQueries OBJECT-TYPE
    SYNTAX      Counter32
    MAX-ACCESS  read-only
    STATUS      obsolete
    DESCRIPTION 
        "this Counter gives the  number of times NetScaler as a 
         name server received a query for an Address Record.

	This object is obsolete.It can be measured through nsDomainServiceName.dnsTotArecQueries. "
    ::= { dnsServerStatistics 11 }

nsRecQueries OBJECT-TYPE
    SYNTAX      Counter32
    MAX-ACCESS  read-only
    STATUS      obsolete
    DESCRIPTION 
        "this Counter gives the  number of times NetScaler as a 
         name server received a query for a name server Record. 

	This object is obsolete.It can be measured through nsDomainServiceName.dnsTotNSrecQueries."
    ::= { dnsServerStatistics 12 }

mxRecQueries OBJECT-TYPE
    SYNTAX      Counter32
    MAX-ACCESS  read-only
    STATUS      obsolete
    DESCRIPTION 
        "this Counter gives the  number of times NetScaler as a 
         name server received a query for an mail exchanger Record. 

	This object is obsolete.It can be measured through nsDomainServiceName.dnsTotMXrecQueries."
    ::= { dnsServerStatistics 13 }

soaRecQueries OBJECT-TYPE
    SYNTAX      Counter32
    MAX-ACCESS  read-only
    STATUS      obsolete
    DESCRIPTION 
        "this Counter gives the  number of times NetScaler as a 
         name server received a query for an SOA Record. 

	This object is obsolete.It can be measured through nsDomainServiceName.dnsTotSOArecQueries."
    ::= { dnsServerStatistics 14 }

cnameRecQueries OBJECT-TYPE
    SYNTAX      Counter32
    MAX-ACCESS  read-only
    STATUS      obsolete
    DESCRIPTION 
        "this Counter gives the  number of times NetScaler as a 
         name server received a query for an CNAME Record.

	This object is obsolete.It can be measured through nsDomainServiceName.dnsTotCNAMErecQueries. "
    ::= { dnsServerStatistics 15 }

totUnsupportedQueries OBJECT-TYPE
    SYNTAX      Counter32
    MAX-ACCESS  read-only
    STATUS      obsolete
    DESCRIPTION 
        "this Counter gives the  number of times NetScaler as a 
         name server received a query for an unsupported Record type. 

	This object is obsolete.It can be measured through nsDomainServiceName.dnsTotUnsupportedQueries."
    ::= { dnsServerStatistics 16 }

dnsServerConfig OBJECT IDENTIFIER
    ::= { dnsServer 2 }

dnsServerRecursion OBJECT-TYPE
    SYNTAX      INTEGER { available(1), restricted(2), unavailable(3) }
    MAX-ACCESS  read-only
    STATUS      obsolete
    DESCRIPTION 
        "This represents the recursion services offered by this
         name server.  The values that can be read are:
         
         available(1) - performs recursion on requests from
         clients.
         
         restricted(2) - recursion is performed on requests only
         from certain clients, for example; clients on an access
         control list.
         
         unavailable(3) - recursion is not available.

	This object is obsolete."
    ::= { dnsServerConfig 1 }

dnsServerZoneTable OBJECT-TYPE
    SYNTAX      SEQUENCE OF DnsServerZoneEntry
    MAX-ACCESS  not-accessible
    STATUS      obsolete
    DESCRIPTION 
        "The table that has the configuration information 
         for each zone for which NetScaler is authoritative.

	This Table is obsolete."
    ::= { dnsServerConfig 2 }

dnsServerZoneEntry OBJECT-TYPE
    SYNTAX      DnsServerZoneEntry
    MAX-ACCESS  not-accessible
    STATUS      obsolete
    DESCRIPTION 
        "The Zone information for each domain as an entry.

	This Entry is obsolete."
    INDEX       { zoneIndex }
    ::= { dnsServerZoneTable 1 }

DnsServerZoneEntry ::= SEQUENCE {
    zoneIndex   Integer32,
    zoneName    OCTET STRING
}

zoneIndex OBJECT-TYPE
    SYNTAX      Integer32
    MAX-ACCESS  read-only
    STATUS      obsolete
    DESCRIPTION 
        "The distinguishing Id for each zone on NetScaler.

	This object is obsolete."
    ::= { dnsServerZoneEntry 1 }

zoneName OBJECT-TYPE
    SYNTAX      OCTET STRING
    MAX-ACCESS  read-only
    STATUS      obsolete
    DESCRIPTION 
        "The domain name.

	This object is obsolete."
    ::= { dnsServerZoneEntry 2 }

globalServerLB OBJECT IDENTIFIER
    ::= { nsRoot 10 }

gslbStatistics OBJECT IDENTIFIER
    ::= { globalServerLB 1 }

gslbDomainStatsTable OBJECT-TYPE
    SYNTAX      SEQUENCE OF GslbDomainStatsEntry
    MAX-ACCESS  not-accessible
    STATUS      obsolete
    DESCRIPTION 
        "The table that has statistics for each gslb domain 
         on netscaler.OBSOLETE"
    ::= { gslbStatistics 1 }

gslbDomainStatsEntry OBJECT-TYPE
    SYNTAX      GslbDomainStatsEntry
    MAX-ACCESS  not-accessible
    STATUS      obsolete
    DESCRIPTION 
        "The gslb statistics table entry. OBSOLETE"
    INDEX       { gslbDomainIndex }
    ::= { gslbDomainStatsTable 1 }

GslbDomainStatsEntry ::= SEQUENCE {
    gslbDomainIndex     Integer32,
    domainname          OCTET STRING,
    gslbDomainQueries   Counter32
}

gslbDomainIndex OBJECT-TYPE
    SYNTAX      Integer32
    MAX-ACCESS  read-only
    STATUS      obsolete
    DESCRIPTION 
        "The distinguishing Id for each gslb Domain on NetScaler. OBSOLETE"
    ::= { gslbDomainStatsEntry 1 }

domainname OBJECT-TYPE
    SYNTAX      OCTET STRING
    MAX-ACCESS  read-only
    STATUS      obsolete
    DESCRIPTION 
        "The domain name that has gslb feature enabled. OBSOLETE"
    ::= { gslbDomainStatsEntry 2 }

gslbDomainQueries OBJECT-TYPE
    SYNTAX      Counter32
    MAX-ACCESS  read-only
    STATUS      obsolete
    DESCRIPTION 
        "number of times a dns query against this gslb domain
         was received by the netscaler. OBSOLETE"
    ::= { gslbDomainStatsEntry 3 }

gslbConfig OBJECT IDENTIFIER
    ::= { globalServerLB 2 }

gslbDomainConfigTable OBJECT-TYPE
    SYNTAX      SEQUENCE OF GslbDomainConfigEntry
    MAX-ACCESS  not-accessible
    STATUS      obsolete
    DESCRIPTION 
        "The table that has configuration for each gslb domain 
         on netscaler.OBSOLETE"
    ::= { gslbConfig 1 }

gslbDomainConfigEntry OBJECT-TYPE
    SYNTAX      GslbDomainConfigEntry
    MAX-ACCESS  not-accessible
    STATUS      obsolete
    DESCRIPTION 
        "The gslb statistics table entry. OBSOLETE"
    INDEX       { gslbcDomainIndex }
    ::= { gslbDomainConfigTable 1 }

GslbDomainConfigEntry ::= SEQUENCE {
    gslbcDomainIndex     Integer32,
    gslbcDomainName          OCTET STRING,
    gslbVipName         OCTET STRING,
    reOrderInterval     TimeTicks
}

gslbcDomainIndex OBJECT-TYPE
    SYNTAX      Integer32
    MAX-ACCESS  read-only
    STATUS      obsolete
    DESCRIPTION 
        "The distinguishing Id for each gslb Domain on NetScaler.OBSOLETE"
    ::= { gslbDomainConfigEntry 1 }

gslbcDomainName OBJECT-TYPE
    SYNTAX      OCTET STRING
    MAX-ACCESS  read-only
    STATUS      obsolete
    DESCRIPTION 
        "The domain name that has gslb feature enabled.OBSOLETE"
    ::= { gslbDomainConfigEntry 2 }

gslbVipName OBJECT-TYPE
    SYNTAX      OCTET STRING
    MAX-ACCESS  read-only
    STATUS      obsolete
    DESCRIPTION 
        "The LB VIP thats bound to the gslb domain name. All the 
         IP addresses for the gslb domain are bound to this VIP.
         The characteristics for this VIP should be found in the 
         LoadBalancing Group Mib. OBSOLETE"
    ::= { gslbDomainConfigEntry 3 }

reOrderInterval OBJECT-TYPE
    SYNTAX      TimeTicks
    MAX-ACCESS  read-only
    STATUS      obsolete
    DESCRIPTION 
        "The interval in which metrics are exchanged among the 
         NetScalers and a decision made about which is the best
         IP address at that point for the gslb domain name. OBSOLETE"
    ::= { gslbDomainConfigEntry 4 }

pq OBJECT IDENTIFIER
    ::= { nsRoot 11 }

pqstatistics OBJECT IDENTIFIER
    ::= { pq 1 }

pqStatsperLBVipTable OBJECT-TYPE
    SYNTAX      SEQUENCE OF PqStatsperLBVipEntry
    MAX-ACCESS  not-accessible
    STATUS      obsolete
    DESCRIPTION 
        "The table that has statistics for each LB Vip 
         on netscaler.

	This Table is obsolete."
    ::= { pqstatistics 1 }

pqStatsperLBVipEntry OBJECT-TYPE
    SYNTAX      PqStatsperLBVipEntry
    MAX-ACCESS  not-accessible
    STATUS      obsolete
    DESCRIPTION 
        "The PQ statistics per Load Balancing VIP entry.

	This Entry is obsolete."
    INDEX       { pqDevno }
    ::= { pqStatsperLBVipTable 1 }

PqStatsperLBVipEntry ::= SEQUENCE {
    pqDevno                       Integer32,
    totclienttransactiontime    Counter32,
    totclienttransaction        Counter32,
    dropped                     Counter32,
    qdepth                      Counter32
}

pqDevno OBJECT-TYPE
    SYNTAX      Integer32
    MAX-ACCESS  read-only
    STATUS      obsolete
    DESCRIPTION 
        "The distinguishing id for the LoadBalancing Vserver.

	This object is obsolete."
    ::= { pqStatsperLBVipEntry 1 }

totclienttransactiontime OBJECT-TYPE
    SYNTAX      Counter32
    MAX-ACCESS  read-only
    STATUS      obsolete
    DESCRIPTION 
        "Total client transaction time.

	This object is obsolete. "
    ::= { pqStatsperLBVipEntry 2 }

totclienttransaction OBJECT-TYPE
    SYNTAX      Counter32
    MAX-ACCESS  read-only
    STATUS      obsolete
    DESCRIPTION 
        "Total number of client transaction.

	This object is obsolete. "
    ::= { pqStatsperLBVipEntry 3 }

dropped OBJECT-TYPE
    SYNTAX      Counter32
    MAX-ACCESS  read-only
    STATUS      obsolete
    DESCRIPTION 
        "Number of dropped transactions.

	This object is obsolete. "
    ::= { pqStatsperLBVipEntry 4 }

qdepth OBJECT-TYPE
    SYNTAX      Counter32
    MAX-ACCESS  read-only
    STATUS      obsolete
    DESCRIPTION 
        "Number of waiting clients .

	This object is obsolete."
    ::= { pqStatsperLBVipEntry 5 }

pqStatsperpqpolicyandperLBVipTable OBJECT-TYPE
    SYNTAX      SEQUENCE OF PqStatsperpqpolicyandperLBVipEntry
    MAX-ACCESS  not-accessible
    STATUS      obsolete
    DESCRIPTION 
        "The table that has statistics for each LB Vip 
         on netscaler.

	This Table is obsolete.Instead of this table use nsVserverGroup.vserverPqpolicyTable."
    ::= { pqstatistics 2 }

pqStatsperpqpolicyandperLBVipEntry OBJECT-TYPE
    SYNTAX      PqStatsperpqpolicyandperLBVipEntry
    MAX-ACCESS  not-accessible
    STATUS      obsolete
    DESCRIPTION 
        "The PQ statistics per Load Balancing VIP entry.

	This Entry is obsolete.Instead of this entry use nsVserverGroup.vserverPqpolicyEntry."
    INDEX       { pqvsdevno, pqpoldevno }
    ::= { pqStatsperpqpolicyandperLBVipTable 1 }

PqStatsperpqpolicyandperLBVipEntry ::= SEQUENCE {
    pqvsdevno                     Integer32,
    pqpoldevno                  Integer32,
    pqtotclienttransactiontime    Counter32,
    pqtotclienttransaction        Counter32,
    pqDropped                     Counter32,
    pqQdepth                      Counter32
}

pqvsdevno OBJECT-TYPE
    SYNTAX      Integer32
    MAX-ACCESS  read-only
    STATUS      obsolete
    DESCRIPTION 
        "The distinguishing id for the LoadBalancing Vservice.

	This object is obsolete."
    ::= { pqStatsperpqpolicyandperLBVipEntry 1 }

pqpoldevno OBJECT-TYPE
    SYNTAX      Integer32
    MAX-ACCESS  read-only
    STATUS      obsolete
    DESCRIPTION 
        "The distinguishing id for the PQ policy.

	This object is obsolete."
    ::= { pqStatsperpqpolicyandperLBVipEntry 2 }

pqtotclienttransactiontime OBJECT-TYPE
    SYNTAX      Counter32
    MAX-ACCESS  read-only
    STATUS      obsolete
    DESCRIPTION 
        "Total client transaction time.

	This object is obsolete.It can be measured through vserverPqpolicyTable.pqpolicyTotClientTransactionTime. "
    ::= { pqStatsperpqpolicyandperLBVipEntry 3 }

pqtotclienttransaction OBJECT-TYPE
    SYNTAX      Counter32
    MAX-ACCESS  read-only
    STATUS      obsolete
    DESCRIPTION 
        "Total number of client transaction.

	This object is obsolete.It can be measured through vserverPqpolicyTable.pqpolicyTotClientTransactions. "
    ::= { pqStatsperpqpolicyandperLBVipEntry 4 }

pqDropped OBJECT-TYPE
    SYNTAX      Counter32
    MAX-ACCESS  read-only
    STATUS      obsolete
    DESCRIPTION 
        "Number of dropped transactions.
	
	This object is obsolete.It can be measured through vserverPqpolicyTable.pqpolicyDropped. "
    ::= { pqStatsperpqpolicyandperLBVipEntry 5 }

pqQdepth OBJECT-TYPE
    SYNTAX      Counter32
    MAX-ACCESS  read-only
    STATUS      obsolete
    DESCRIPTION 
        "Number of waiting clients.

	This object is obsolete.It can be measured through vserverPqpolicyTable.pqpolicyQdepth. "
    ::= { pqStatsperpqpolicyandperLBVipEntry 6 }

pqconfig OBJECT IDENTIFIER
    ::= { pq 2 }

pqpolicyconfigTable OBJECT-TYPE
    SYNTAX      SEQUENCE OF PqpolicyconfigEntry
    MAX-ACCESS  not-accessible
    STATUS      obsolete
    DESCRIPTION 
        "The table that has configuration statistics for each PQ
         policy on netscaler.

	This Table is obsolete.Instead of this table use nsPqPolicyGroup.pqPolicyConfigTable."
    ::= { pqconfig 1 }

pqpolicyconfigEntry OBJECT-TYPE
    SYNTAX      PqpolicyconfigEntry
    MAX-ACCESS  not-accessible
    STATUS      obsolete
    DESCRIPTION 
        "The PQ config statistics per policy.

	This Entry is obsolete.Instead of this entry use nsPqPolicyGroup.pqPolicyConfigEntry."
    INDEX       { pqPolDevno }
    ::= { pqpolicyconfigTable 1 }

PqpolicyconfigEntry ::= SEQUENCE {
    pqPolDevno               Integer32,
    pqpolicyname        OCTET STRING,
    rulename            OCTET STRING,
    qdepthThreshval     Integer32,
    polqdepthThreshval  Integer32,
    priority            Integer32,
    pqPolWeight              Integer32
}

pqPolDevno OBJECT-TYPE
    SYNTAX      Integer32
    MAX-ACCESS  read-only
    STATUS      obsolete
    DESCRIPTION 
        "The distinguishing id for the policy.

	This object is obsolete."
    ::= { pqpolicyconfigEntry 1 }

pqpolicyname OBJECT-TYPE
    SYNTAX      OCTET STRING
    MAX-ACCESS  read-only
    STATUS      obsolete
    DESCRIPTION 
        "The name for PQ policyi.

	This object is obsolete.It can be measured through pqPolicyConfigTable.pqName."
    ::= { pqpolicyconfigEntry 2 }

rulename OBJECT-TYPE
    SYNTAX      OCTET STRING
    MAX-ACCESS  read-only
    STATUS      obsolete
    DESCRIPTION 
        "The rule name.

	This object is obsolete.It can be measured through pqPolicyConfigTable.pqRuleName."
    ::= { pqpolicyconfigEntry 3 }

qdepthThreshval OBJECT-TYPE
    SYNTAX      Integer32
    MAX-ACCESS  read-only
    STATUS      obsolete
    DESCRIPTION 
        "The threshold value for qdepth.

	This object is obsolete.It can be measured through pqPolicyConfigTable.pqQdepthThreshval."
    ::= { pqpolicyconfigEntry 4 }

polqdepthThreshval OBJECT-TYPE
    SYNTAX      Integer32
    MAX-ACCESS  read-only
    STATUS      obsolete
    DESCRIPTION 
        "The threshold value for policyqdepth.

	This object is obsolete.It can be measured through pqPolicyConfigTable.pqPolQdepthThreshval."
    ::= { pqpolicyconfigEntry 5 }

priority OBJECT-TYPE
    SYNTAX      Integer32
    MAX-ACCESS  read-only
    STATUS      obsolete
    DESCRIPTION 
        "The priority for this pq policy.

	This object is obsolete.It can be measured through pqPolicyConfigTable.pqPriority."
    ::= { pqpolicyconfigEntry 6 }

pqPolWeight OBJECT-TYPE
    SYNTAX      Integer32
    MAX-ACCESS  read-only
    STATUS      obsolete
    DESCRIPTION 
        "The weight for the priority.

	This object is obsolete.It can be measured through pqPolicyConfigTable.pqPolicyWeight."
    ::= { pqpolicyconfigEntry 7 }

dos OBJECT IDENTIFIER
    ::= { nsRoot 12 }

dosstatistics OBJECT IDENTIFIER
    ::= { dos 1 }

dosservicestatsTable OBJECT-TYPE
    SYNTAX      SEQUENCE OF DosservicestatsEntry
    MAX-ACCESS  not-accessible
    STATUS      obsolete
    DESCRIPTION 
        "The table that has statistics for each LB Vip.

	This Table is obsolete.Instead of this table use nsSvcGroup.serviceTable."
    ::= { dosstatistics 1 }

dosservicestatsEntry OBJECT-TYPE
    SYNTAX      DosservicestatsEntry
    MAX-ACCESS  not-accessible
    STATUS      obsolete
    DESCRIPTION 
        "The DOS service statistics per Load Balancing VIP entry.

	This Entry is obsolete.Instead of this entry use nsSvcGroup.serviceEntry."
    INDEX       { dosDevno }
    ::= { dosservicestatsTable 1 }

DosservicestatsEntry ::= SEQUENCE {
    dosDevno               Integer32,
    surgecnt            Counter32,
    dosqdepth           Counter32,
    totaljstransaction  Counter32
}

dosDevno OBJECT-TYPE
    SYNTAX      Integer32
    MAX-ACCESS  read-only
    STATUS      obsolete
    DESCRIPTION 
        "The distinguishing id for the LoadBalancing Vserver.

	This object is obsolete."
    ::= { dosservicestatsEntry 1 }

surgecnt OBJECT-TYPE
    SYNTAX      Counter32
    MAX-ACCESS  read-only
    STATUS      obsolete
    DESCRIPTION 
        "The qdepth on this service.

	This object is obsolete.It can be measured through serviceTable.svcSurgeCount."
    ::= { dosservicestatsEntry 2 }

dosqdepth OBJECT-TYPE
    SYNTAX      Counter32
    MAX-ACCESS  read-only
    STATUS      obsolete
    DESCRIPTION 
        "The number of genuine clients on this service.

	This object is obsolete.It can be measured through serviceTable.svcdosQDepth."
    ::= { dosservicestatsEntry 3 }

totaljstransaction OBJECT-TYPE
    SYNTAX      Counter32
    MAX-ACCESS  read-only
    STATUS      obsolete
    DESCRIPTION 
        "The total number of javascripts sent to genuine clients.

	This object is obsolete.It can be measured through serviceTable.svctotalJsTransaction. "
    ::= { dosservicestatsEntry 4 }

dosconfig OBJECT IDENTIFIER
    ::= { dos 2 }

dospolicyconfigTable OBJECT-TYPE
    SYNTAX      SEQUENCE OF DospolicyconfigEntry
    MAX-ACCESS  not-accessible
    STATUS      obsolete
    DESCRIPTION 
        "The table that has statistics for each policy 
         on netscaler.

	This Table is obsolete.Instead of this table use nsDosPolicyGroup.dosPolicyTable."
    ::= { dosconfig 1 }

dospolicyconfigEntry OBJECT-TYPE
    SYNTAX      DospolicyconfigEntry
    MAX-ACCESS  not-accessible
    STATUS      obsolete
    DESCRIPTION 
        "The entry for DOS policy configuration.
	
	This Entry is obsolete.Instead of this entry use nsDosPolicyGroup.dosPolicyEntry."
    INDEX       { dosPolDevno }
    ::= { dospolicyconfigTable 1 }

DospolicyconfigEntry ::= SEQUENCE {
    dosPolDevno           Integer32,
    dospolicyname   OCTET STRING,
    thresholdvalue  Integer32
}

dosPolDevno OBJECT-TYPE
    SYNTAX      Integer32
    MAX-ACCESS  read-only
    STATUS      obsolete
    DESCRIPTION 
        "The distinguishing id for the configured DOS policies.

	This object is obsolete."
    ::= { dospolicyconfigEntry 1 }

dospolicyname OBJECT-TYPE
    SYNTAX      OCTET STRING
    MAX-ACCESS  read-only
    STATUS      obsolete
    DESCRIPTION 
        "The name of the DOS policy.

	This object is obsolete.It can be measured through dosPolicyTable.dosPolicyName."
    ::= { dospolicyconfigEntry 2 }

thresholdvalue OBJECT-TYPE
    SYNTAX      Integer32
    MAX-ACCESS  read-only
    STATUS      obsolete
    DESCRIPTION 
        "The value of qdepth at which DOS protection gets triggered.

	This object is obsolete.It can be measured through dosPolicyTable.thresholdValue."
    ::= { dospolicyconfigEntry 3 }

ssloffloading OBJECT IDENTIFIER
    ::= { nsRoot 13 }

sslstatistics OBJECT IDENTIFIER
    ::= { ssloffloading 1 }

sslglobalstats OBJECT IDENTIFIER
    ::= { sslstatistics 1 }

currSPS OBJECT-TYPE
    SYNTAX      Counter32
    MAX-ACCESS  read-only
    STATUS      obsolete
    DESCRIPTION 
        "SSL session/second between client and NetScaler"
    ::= { sslglobalstats 1 }

sslV2TxCount OBJECT-TYPE
	SYNTAX Counter32
	MAX-ACCESS read-only
	STATUS obsolete
	DESCRIPTION
		"Total number of SSL v2 Transactions"
	::= { sslglobalstats 2 }

sslV3TxCount OBJECT-TYPE
	SYNTAX Counter32
	MAX-ACCESS read-only
	STATUS obsolete
	DESCRIPTION
		"Total number of SSL v3 Transactions"
	::= { sslglobalstats 3 }

tlsV1TxCount OBJECT-TYPE
	SYNTAX Counter32
	MAX-ACCESS read-only
	STATUS obsolete
	DESCRIPTION
		"Total number of TLS v1 Transactions"
	::= { sslglobalstats 4 }

keyExRSA512 OBJECT-TYPE
	SYNTAX Counter32
	MAX-ACCESS read-only
	STATUS obsolete
	DESCRIPTION
		"Total number of 512 bit RSA key exchange"
	::= { sslglobalstats 5 }
		
keyExRSA1024 OBJECT-TYPE
	SYNTAX Counter32
	MAX-ACCESS read-only
	STATUS obsolete
	DESCRIPTION
		"Total number of 1024 bit RSA key exchange"
	::= { sslglobalstats 6 }

keyExDH512 OBJECT-TYPE
	SYNTAX Counter32
	MAX-ACCESS read-only
	STATUS obsolete
	DESCRIPTION
		"Total number of 512 bit DH key exchange"
	::= { sslglobalstats 7 }

keyExDH1024 OBJECT-TYPE
	SYNTAX Counter32
	MAX-ACCESS read-only
	STATUS obsolete
	DESCRIPTION
		"Total number of 1024 bit DH key exchange"
	::= { sslglobalstats 8 }

authRSA OBJECT-TYPE
	SYNTAX Counter32
	MAX-ACCESS read-only
	STATUS obsolete
	DESCRIPTION
		"Total number of RSA authentication"
	::= { sslglobalstats 9 }
		
authDH OBJECT-TYPE
	SYNTAX Counter32
	MAX-ACCESS read-only
	STATUS obsolete
	DESCRIPTION
		"Total number of DH authentication"
	::= { sslglobalstats 10 }

authDS OBJECT-TYPE
	SYNTAX Counter32
	MAX-ACCESS read-only
	STATUS obsolete
	DESCRIPTION
		"Total number of DS authentication"
	::= { sslglobalstats 11 }

cipher40BitRC4 OBJECT-TYPE
	SYNTAX Counter32
	MAX-ACCESS read-only
	STATUS obsolete
	DESCRIPTION
			"Total number of RC4-40 cipher used"
	::= { sslglobalstats 12 }

cipher56BitRC4 OBJECT-TYPE
	SYNTAX Counter32
	MAX-ACCESS read-only
	STATUS obsolete
	DESCRIPTION
		"Total number of RC4-56 cipher used"
	::= { sslglobalstats 13 }

cipher64BitRC4 OBJECT-TYPE
	SYNTAX Counter32
	MAX-ACCESS read-only
	STATUS obsolete
	DESCRIPTION
		"Total number of RC4-64 cipher used"
	::= { sslglobalstats 14 }

cipher128BitRC4 OBJECT-TYPE
	SYNTAX Counter32
	MAX-ACCESS read-only
	STATUS obsolete
	DESCRIPTION
		"Total number of RC4-128 cipher used"
	::= { sslglobalstats 15 }


cipher40BitDES OBJECT-TYPE
	SYNTAX Counter32
	MAX-ACCESS read-only
	STATUS obsolete
	DESCRIPTION
		"Total number of DES-40 cipher used"
	::= { sslglobalstats 16 }

cipher56BitDES OBJECT-TYPE
	SYNTAX Counter32
	MAX-ACCESS read-only
	STATUS obsolete
	DESCRIPTION
		"Total number of DES-56 cipher used"
	::= { sslglobalstats 17 }


cipher168Bit3DES OBJECT-TYPE
	SYNTAX Counter32
	MAX-ACCESS read-only
	STATUS obsolete
	DESCRIPTION
		"Total number of 3DES-168 cipher used"
	::= { sslglobalstats 18 }


cipher40BitRC2 OBJECT-TYPE
	SYNTAX Counter32
	MAX-ACCESS read-only
	STATUS obsolete
	DESCRIPTION
		"Total number of RC2-40 cipher used"
	::= { sslglobalstats 19 }

cipher56BitRC2 OBJECT-TYPE
	SYNTAX Counter32
	MAX-ACCESS read-only
	STATUS obsolete
	DESCRIPTION
		"Total number of RC2-56 cipher used"
	::= { sslglobalstats 20 }


cipher128BitRC2 OBJECT-TYPE
	SYNTAX Counter32
	MAX-ACCESS read-only
	STATUS obsolete
	DESCRIPTION
		"Total number of RC2-128 cipher used"
	::= { sslglobalstats 21 }

cipher128BitIDEA OBJECT-TYPE
	SYNTAX Counter32
	MAX-ACCESS read-only
	STATUS obsolete
	DESCRIPTION
		"Total number of IDEA-128 cipher used"
	::= { sslglobalstats 22 }

hashMD5 OBJECT-TYPE
	SYNTAX Counter32
	MAX-ACCESS read-only
	STATUS obsolete
	DESCRIPTION
		"Total number of HASH-MD5 hash used"
	::= { sslglobalstats 23 }

hashSHA OBJECT-TYPE
	SYNTAX Counter32
	MAX-ACCESS read-only
	STATUS obsolete
	DESCRIPTION
		"Total number of HASH_SHA hash used"
	::= { sslglobalstats 24 }

sslConfig OBJECT IDENTIFIER
    ::= { ssloffloading 2 }

certKeyTable OBJECT-TYPE
    SYNTAX      SEQUENCE OF CertKeyEntry
    MAX-ACCESS  not-accessible
    STATUS      obsolete
    DESCRIPTION 
        "The table that has all the configuration information for 
         each certificate key pair.

	This Table is obsolete.Instead of this table use nsSslConfigGroup.sslCertKeyTable."
    ::= { sslConfig 1 }

certKeyEntry OBJECT-TYPE
    SYNTAX      CertKeyEntry
    MAX-ACCESS  not-accessible
    STATUS      obsolete
    DESCRIPTION 
        "The certificate key pair information for each entry.

	This Entry is obsolete.Instead of this entry use nsSslConfigGroup.sslCertKeyEntry."
    INDEX       { certKeyId }
    ::= { certKeyTable 1 }

CertKeyEntry ::= SEQUENCE {
    certKeyId       Integer32,
    certKeyName     OCTET STRING,
    certPath        OCTET STRING,
    keyPath         OCTET STRING,
    inputFormat     INTEGER
}

certKeyId OBJECT-TYPE
    SYNTAX      Integer32
    MAX-ACCESS  read-only
    STATUS      obsolete
    DESCRIPTION 
        "The Distinguish ID for each certificate key pair in NetScaler.

	This object is obsolete."
    ::= { certKeyEntry 1 }

certKeyName OBJECT-TYPE
    SYNTAX      OCTET STRING
    MAX-ACCESS  read-only
    STATUS      obsolete
    DESCRIPTION 
        "The certificate key pair Name.

	This object is obsolete.It can be measured through sslCertKeyTable.sslCertKeyName."
    ::= { certKeyEntry 2 }

certPath OBJECT-TYPE
    SYNTAX      OCTET STRING
    MAX-ACCESS  read-only
    STATUS      obsolete
    DESCRIPTION 
        "The certificate path.

	This object is obsolete.It can be measured through sslCertKeyTable.sslCertPath."
    ::= { certKeyEntry 3 }

keyPath OBJECT-TYPE
    SYNTAX      OCTET STRING
    MAX-ACCESS  read-only
    STATUS      obsolete
    DESCRIPTION 
        "The private key path.

	This object is obsolete.It can be measured through sslCertKeyTable.sslKeyPath."
    ::= { certKeyEntry 4 }

inputFormat OBJECT-TYPE
    SYNTAX      INTEGER { der(1), pem(3) }
    MAX-ACCESS  read-only
    STATUS      obsolete
    DESCRIPTION 
        "The input format of the certificate key pair.

	This object is obsolete.It can be measured through sslCertKeyTable.sslInputFormat."
    ::= { certKeyEntry 5 }

crlTable OBJECT-TYPE
    SYNTAX      SEQUENCE OF CrlEntry
    MAX-ACCESS  not-accessible
    STATUS      obsolete
    DESCRIPTION 
        "The table that has all the configuration 
         information for each CRL in NetScaler.

	This Table is obsolete.Instead of this table use nsSslConfigGroup.sslCrlTable."
    ::= { sslConfig 2 }

crlEntry OBJECT-TYPE
    SYNTAX      CrlEntry
    MAX-ACCESS  not-accessible
    STATUS      obsolete
    DESCRIPTION 
        "The CRL information for each entry.

	This Entry is obsolete.Instead of this entry use nsSslConfigGroup.sslCrlEntry."
    INDEX       { crlId }
    ::= { crlTable 1 }

CrlEntry ::= SEQUENCE {
	crlId	Integer32,
	crlName	OCTET STRING,
	crlPath	OCTET STRING,
    crlInputFormat     INTEGER
}
  
crlId  OBJECT-TYPE
	SYNTAX Integer32
    MAX-ACCESS  read-only
	STATUS obsolete
	DESCRIPTION		
		"The Distinguish ID for each CRL in NetScaler.

	This object is obsolete."
	::= { crlEntry 1 }


crlName OBJECT-TYPE
  	SYNTAX OCTET STRING
	MAX-ACCESS read-only
	STATUS obsolete
	DESCRIPTION	
		"The name of CRL.

	This object is obsolete.It can be measured through sslCrlTable.sslCrlName."
	::= { crlEntry 2 }


crlPath OBJECT-TYPE
  	SYNTAX OCTET STRING
	MAX-ACCESS read-only
	STATUS obsolete
	DESCRIPTION	
		"The CRL path.

	This object is obsolete.It can be measured through sslCrlTable.sslCrlPath."
	::= { crlEntry 3 }

  
crlInputFormat OBJECT-TYPE
    SYNTAX      INTEGER { der(1), pem(3) }
    MAX-ACCESS  read-only
    STATUS      obsolete
    DESCRIPTION 
        "The input format of CRL.

	This object is obsolete.It can be measured through sslCrlTable.sslCrlInputFormat."
    ::= { crlEntry 4 }
                
cipherGroupTable OBJECT-TYPE
    SYNTAX      SEQUENCE OF CipherGroupEntry
    MAX-ACCESS  not-accessible
    STATUS      obsolete
    DESCRIPTION 
        "The table that has all the configuration information
         for each cipher group in NetScaler.

	This Table is obsolete.Instead of this table use nsSslConfigGroup.sslCipherGroupTable."
    ::= { sslConfig 3 }

cipherGroupEntry OBJECT-TYPE
    SYNTAX      CipherGroupEntry
    MAX-ACCESS  not-accessible
    STATUS      obsolete
    DESCRIPTION 
        "The Cipher group information for each entry.

	This Entry is obsolete.Instead of this entry use sslCipherGroupTable.sslCipherGroupEntry."
    INDEX       { cipherGroupId, cipherId }
    ::= { cipherGroupTable 1 }

CipherGroupEntry ::= SEQUENCE {
    cipherGroupId       Integer32,
    cipherId            Integer32,
    cipherGroupName     OCTET STRING,
    cipherName          OCTET STRING,
    cipherDesc          OCTET STRING
}

cipherGroupId OBJECT-TYPE
    SYNTAX      Integer32
    MAX-ACCESS  read-only
    STATUS      obsolete
    DESCRIPTION 
        "The Distinguish ID for each Cipher group in NetScaler.

	This object is obsolete."
    ::= { cipherGroupEntry 1 }

cipherId OBJECT-TYPE
    SYNTAX      Integer32
    MAX-ACCESS  read-only
    STATUS      obsolete
    DESCRIPTION 
        "The Distinguish ID for each Cipher in NetScaler.

	This object is obsolete."
    ::= { cipherGroupEntry 2 }

cipherGroupName OBJECT-TYPE
    SYNTAX      OCTET STRING
    MAX-ACCESS  read-only
    STATUS      obsolete
    DESCRIPTION 
        "The Cipher group name.

	This object is obsolete.It can not be measured through sslCipherGroupTable.sslCipherGroupName.	"
    ::= { cipherGroupEntry 3 }

cipherName OBJECT-TYPE
    SYNTAX      OCTET STRING
    MAX-ACCESS  read-only
    STATUS      obsolete
    DESCRIPTION 
        "The Cipher name.

	This object is obsolete.It can not be measured through sslCipherGroupTable.sslCipherName."
    ::= { cipherGroupEntry 4 }

cipherDesc OBJECT-TYPE
    SYNTAX      OCTET STRING
    MAX-ACCESS  read-only
    STATUS      obsolete
    DESCRIPTION 
        "The Cipher description.

	This object is obsolete.It can not be measured through sslCipherGroupTable.sslCipherDesc."
    ::= { cipherGroupEntry 5 }

advanceSSLConfigTable OBJECT-TYPE
    SYNTAX      SEQUENCE OF AdvanceSSLConfigEntry
    MAX-ACCESS  not-accessible
    STATUS      obsolete
    DESCRIPTION 
        "The table that has all the advance SSL configuration
         information for each  virtual/physical service in NetScaler.

	This Table is obsolete.Instead of this table use nsSvcGroup.serviceAdvanceSslConfigTable or nsVserverGroup.vserverAdvanceSslConfigTable."
    ::= { sslConfig 4 }

advanceSSLConfigEntry OBJECT-TYPE
    SYNTAX      AdvanceSSLConfigEntry
    MAX-ACCESS  not-accessible
    STATUS      obsolete
    DESCRIPTION 
        "The advance SSL configuration for each entry.

	This Entry is obsolete.Instead of this entry use nsSvcGroup.serviceAdvanceSslConfigEntry or nsVserverGroup.vserverAdvanceSslConfigEntry."
    INDEX       { id }
    ::= { advanceSSLConfigTable 1 }

AdvanceSSLConfigEntry ::= SEQUENCE {
	id	Integer32,
	serviceName	OCTET STRING,
	dh	INTEGER,
	dhCount	Integer32,
	dhFile	OCTET STRING,
    eRSA            INTEGER,
    eRSACount       Integer32,
    certHeader      INTEGER,
    certHeaderTag   OCTET STRING,
    sessHeader      INTEGER,
    sessHeaderTag   OCTET STRING,
    sslv2           INTEGER,
    sslv3           INTEGER,
    tlsv1           INTEGER,
    owaSupport      INTEGER,
    sslRedirect     INTEGER,
    clearTextPort   Integer32,
    serviceType     INTEGER
}
 
id	OBJECT-TYPE
	SYNTAX Integer32
	MAX-ACCESS  read-only
	STATUS obsolete   
	DESCRIPTION	
		"The Distinguish ID for each SSL virtual/physical service in NetScaler.

	This object is obsolete."
	::= { advanceSSLConfigEntry 1 }

serviceName	OBJECT-TYPE
  	SYNTAX OCTET STRING
	MAX-ACCESS read-only
	STATUS obsolete
	DESCRIPTION	
		"The service name.

	This object is obsolete.It can be measured."
	::= { advanceSSLConfigEntry 2 }

dh OBJECT-TYPE
	SYNTAX INTEGER {disabled(1),enabled(2)}
	MAX-ACCESS  read-only
	STATUS obsolete
	DESCRIPTION	
		"Whether DH is enabled/disabled.

	This object is obsolete.It can be measured through serviceAdvanceSslConfigTable.svcSslDH or vserverAdvanceSslConfigTable.vsvrSslDH."
	::= { advanceSSLConfigEntry 3 }

dhCount OBJECT-TYPE
	SYNTAX Integer32
	MAX-ACCESS read-only
	STATUS obsolete
	DESCRIPTION	
		"The DH refresh count to re-generate public/private key.

	This object is obsolete.It can be measured through serviceAdvanceSslConfigTable.svcSslDHCount or vserverAdvanceSslConfigTable.vsvrSslDHCount."
	::= { advanceSSLConfigEntry 4 }

dhFile OBJECT-TYPE
  	SYNTAX OCTET STRING
	MAX-ACCESS read-only
	STATUS obsolete
	DESCRIPTION	
		"The DH file path name.

	This object is obsolete.It can be measured through serviceAdvanceSslConfigTable.svcSslDHFilePath or vserverAdvanceSslConfigTable.vsvrSslDHFilePath."
	::= { advanceSSLConfigEntry 5 }

eRSA OBJECT-TYPE
    SYNTAX      INTEGER { disabled(1), enabled(2) }
    MAX-ACCESS  read-only
    STATUS      obsolete
    DESCRIPTION 
        "The ephimeral RSA support for service.

	This object is obsolete.It can be measured through serviceAdvanceSslConfigTable.svcSsleRSA or vserverAdvanceSslConfigTable.vsvrSsleRSA."
    ::= { advanceSSLConfigEntry 6 }

eRSACount OBJECT-TYPE
    SYNTAX      Integer32
    MAX-ACCESS  read-only
    STATUS      obsolete
    DESCRIPTION 
        "The eRSA refresh count to re-generate RSA temporary key.

	This object is obsolete.It can be measured through serviceAdvanceSslConfigTable.svcSsleRSACount or vserverAdvanceSslConfigTable.vsvrSsleRSACount."
    ::= { advanceSSLConfigEntry 7 }

certHeader OBJECT-TYPE
    SYNTAX      INTEGER { disabled(1), enabled(2) }
    MAX-ACCESS  read-only
    STATUS      obsolete
    DESCRIPTION 
        "The certificate insertion in HTTP request.

	This object is obsolete.It can be measured through serviceAdvanceSslConfigTable.svcSslCertHeader or vserverAdvanceSslConfigTable.vsvrSslCertHeader."
    ::= { advanceSSLConfigEntry 8 }

certHeaderTag OBJECT-TYPE
    SYNTAX      OCTET STRING
    MAX-ACCESS  read-only
    STATUS      obsolete
    DESCRIPTION 
        "The certificate tag name in HTTP request.

	This object is obsolete.It can be measured through serviceAdvanceSslConfigTable.svcSslCertHeaderTag or vserverAdvanceSslConfigTable.vsvrSslCertHeaderTag."
    ::= { advanceSSLConfigEntry 9 }

sessHeader OBJECT-TYPE
    SYNTAX      INTEGER { disabled(1), enabled(2) }
    MAX-ACCESS  read-only
    STATUS      obsolete
    DESCRIPTION 
        "The session id insertion in HTTP request.

	This object is obsolete.It can be measured through serviceAdvanceSslConfigTable.svcSslSessionHeader or vserverAdvanceSslConfigTable.vsvrSslSessionHeader."
    ::= { advanceSSLConfigEntry 10 }

sessHeaderTag OBJECT-TYPE
    SYNTAX      OCTET STRING
    MAX-ACCESS  read-only
    STATUS      obsolete
    DESCRIPTION 
        "The session id tag name in HTTP request.

	This object is obsolete.It can be measured through serviceAdvanceSslConfigTable.svcSslSessionHeaderTag or vserverAdvanceSslConfigTable.vsvrSslSessionHeaderTag."
    ::= { advanceSSLConfigEntry 11 }

sslv2 OBJECT-TYPE
    SYNTAX      INTEGER { disabled(1), enabled(2) }
    MAX-ACCESS  read-only
    STATUS      obsolete
    DESCRIPTION 
        "The support for SSLv2 protocol for service.

	This object is obsolete.It can be measured through serviceAdvanceSslConfigTable.svcSslv2Protocol or vserverAdvanceSslConfigTable.vsvrSslv2Protocol."
    ::= { advanceSSLConfigEntry 12 }

sslv3 OBJECT-TYPE
    SYNTAX      INTEGER { disabled(1), enabled(2) }
    MAX-ACCESS  read-only
    STATUS      obsolete
    DESCRIPTION 
        "The support for SSLv3 protocol for service.

	This object is obsolete.It can be measured through serviceAdvanceSslConfigTable.svcSslv3Protocol or vserverAdvanceSslConfigTable.vsvrSslv3Protocol."
    ::= { advanceSSLConfigEntry 13 }

tlsv1 OBJECT-TYPE
    SYNTAX      INTEGER { disabled(1), enabled(2) }
    MAX-ACCESS  read-only
    STATUS      obsolete
    DESCRIPTION 
        "The support for TLSv1 protocol for service.

	This object is obsolete.It can be measured through serviceAdvanceSslConfigTable.svcSslTLSv1Protocol or vserverAdvanceSslConfigTable.vsvrSslTLSv1Protocol."
    ::= { advanceSSLConfigEntry 14 }

owaSupport OBJECT-TYPE
    SYNTAX      INTEGER { disabled(1), enabled(2) }
    MAX-ACCESS  read-only
    STATUS      obsolete
    DESCRIPTION 
        "The support for outlook web access for service.

	This object is obsolete.It can be measured through serviceAdvanceSslConfigTable.svcSsloutlookSupport or vserverAdvanceSslConfigTable.vsvrSsloutlookSupport."
    ::= { advanceSSLConfigEntry 15 }

sslRedirect OBJECT-TYPE
    SYNTAX      INTEGER { disabled(1), enabled(2) }
    MAX-ACCESS  read-only
    STATUS      obsolete
    DESCRIPTION 
        "The support for ssl redirect for service.

	This object is obsolete.It can be measured through serviceAdvanceSslConfigTable.svcSslRedirectSupport or vserverAdvanceSslConfigTable.vsvrSslRedirectSupport."
    ::= { advanceSSLConfigEntry 16 }

clearTextPort OBJECT-TYPE
    SYNTAX      Integer32
    MAX-ACCESS  read-only
    STATUS      obsolete
    DESCRIPTION 
        "The clear text port on the backend webserver.

	This object is obsolete.It can be measured through serviceAdvanceSslConfigTable.svcSslClearTextPort or vserverAdvanceSslConfigTable.vsvrSslClearTextPort."
    ::= { advanceSSLConfigEntry 17 }

serviceType OBJECT-TYPE
    SYNTAX      INTEGER { virtualserver(0), physicalservice(1) }
    MAX-ACCESS  read-only
    STATUS      obsolete
    DESCRIPTION 
        "The type of the service virtual/ real.

	This object is obsolete."
    ::= { advanceSSLConfigEntry 18 }

certBindingConfigTable OBJECT-TYPE
    SYNTAX      SEQUENCE OF CertBindingConfigEntry
    MAX-ACCESS  not-accessible
    STATUS      obsolete
    DESCRIPTION 
        "The table that has all the certificate configuration 
         for each  service in NetScaler.

	This Table is obsolete."
    ::= { sslConfig 5 }

certBindingConfigEntry OBJECT-TYPE
    SYNTAX      CertBindingConfigEntry
    MAX-ACCESS  not-accessible
    STATUS      obsolete
    DESCRIPTION 
        "The certificate bindings for each entry.

	This Entry is obsolete."
    INDEX       { certBindId, certKeyID, certType }
    ::= { certBindingConfigTable 1 }

CertBindingConfigEntry ::= SEQUENCE {
	certBindId				Integer32,
    certKeyID       Integer32,
    certType		INTEGER,
    certBindServiceName		OCTET STRING,
    certBindKeyName     OCTET STRING,
    certBindServiceType     INTEGER
}

certBindId	OBJECT-TYPE
	SYNTAX Integer32
	MAX-ACCESS read-only
	STATUS obsolete
	DESCRIPTION	
		"The Distinguish ID for each SSL virtual/real service in NetScaler.

	This object is obsolete."
	::= { certBindingConfigEntry 1 }

certKeyID OBJECT-TYPE
    SYNTAX      Integer32
    MAX-ACCESS  read-only
    STATUS      obsolete
    DESCRIPTION 
        "The Distinguish ID for each certificate key pair in NetScaler.

	This object is obsolete."
    ::= { certBindingConfigEntry 2 }
 
certType OBJECT-TYPE
	SYNTAX INTEGER { serverCertificate(1), caCertificate (2) }
	MAX-ACCESS  read-only
	STATUS obsolete
	DESCRIPTION	
		"Whether certificate key pair is CA or not.

	This object is obsolete."
	::= { certBindingConfigEntry 3 }

certBindServiceName     OBJECT-TYPE
	SYNTAX OCTET STRING	
    MAX-ACCESS  read-only
	STATUS obsolete
	DESCRIPTION	
		"The service name.

	This object is obsolete."
	::= { certBindingConfigEntry 4 }

certBindKeyName OBJECT-TYPE
    SYNTAX      OCTET STRING
    MAX-ACCESS  read-only
    STATUS      obsolete
    DESCRIPTION 
        "The certificate key pair name.

	This object is obsolete."
    ::= { certBindingConfigEntry 5 }

certBindServiceType OBJECT-TYPE
    SYNTAX      INTEGER { virtualserver(0), physicalservice(1) }
    MAX-ACCESS  read-only
    STATUS      obsolete
    DESCRIPTION 
        "The type of the service virtual/ real.

	This object is obsolete."
    ::= { certBindingConfigEntry 6 }

cipherBindingConfigTable OBJECT-TYPE
    SYNTAX      SEQUENCE OF CipherBindingConfigEntry
    MAX-ACCESS  not-accessible
    STATUS      obsolete
    DESCRIPTION 
        "The table that has all the cipher configuration for
         each  service in NetScaler.

	This Table is obsolete.Instead of this table use nsSvcGroup.serviceCipherBindingTable or nsVserverGroup.vserverCipherBindingTable."
    ::= { sslConfig 6 }

cipherBindingConfigEntry OBJECT-TYPE
    SYNTAX      CipherBindingConfigEntry
    MAX-ACCESS  not-accessible
    STATUS      obsolete
    DESCRIPTION 
        "The cipher bindings for each entry.

	This Entry is obsolete.Instead of this entry use nsSvcGroup.serviceCipherBindingEntry or nsVserverGroup.vserverCipherBindingEntry."
    INDEX       { cipherBindId, cipherID }
    ::= { cipherBindingConfigTable 1 }

CipherBindingConfigEntry ::= SEQUENCE {
    cipherBindId              Integer32,
    cipherID        Integer32,
    cipherBindServiceName		OCTET STRING,
    cipherbName      OCTET STRING,
    cipherbDesc      OCTET STRING,
    cipherBindServiceType     INTEGER
}

cipherBindId OBJECT-TYPE
    SYNTAX      Integer32
    MAX-ACCESS  read-only
    STATUS      obsolete
    DESCRIPTION 
        "The distinguishing ID for each SSL virtual/real service in NetScaler.

	This object is obsolete."
    ::= { cipherBindingConfigEntry 1 }

cipherID OBJECT-TYPE
    SYNTAX      Integer32
    MAX-ACCESS  read-only
    STATUS      obsolete
    DESCRIPTION 
        "The distinguishing ID for each cipher in NetScaler.

	This object is obsolete."
    ::= { cipherBindingConfigEntry 2 }

cipherBindServiceName	OBJECT-TYPE
	SYNTAX OCTET STRING	
	MAX-ACCESS read-only
	STATUS obsolete
	DESCRIPTION	
		"The name of the physical or virtual service.

	This object is obsolete."
	::= { cipherBindingConfigEntry 3 }

cipherbName OBJECT-TYPE
    SYNTAX      OCTET STRING
    MAX-ACCESS  read-only
    STATUS      obsolete
    DESCRIPTION 
        "The cipher name.

	This object is obsolete.It can be measured through serviceCipherBindingTable.svcSslCipherBindName or vserverCipherBindingTable.vsvrSslCipherBindName."
    ::= { cipherBindingConfigEntry 4 }

cipherbDesc OBJECT-TYPE
    SYNTAX      OCTET STRING
    MAX-ACCESS  read-only
    STATUS      obsolete
    DESCRIPTION 
        "The cipher description.

	This object is obsolete.It can be measured through serviceCipherBindingTable.svcSslCipherBindDesc or vserverCipherBindingTable.vsvrSslCipherBindDesc."
    ::= { cipherBindingConfigEntry 5 }

cipherBindServiceType OBJECT-TYPE
    SYNTAX      INTEGER { virtualserver(0), physicalservice(1) }
    MAX-ACCESS  read-only
    STATUS      obsolete
    DESCRIPTION 
        "The type of the service virtual/ real.

	This object is obsolete."
    ::= { cipherBindingConfigEntry 6 }

cpe OBJECT IDENTIFIER
    ::= { nsRoot 14 }

cpestatistics OBJECT IDENTIFIER
    ::= { cpe 1 }

cpestatspolicyTable OBJECT-TYPE
    SYNTAX      SEQUENCE OF CpestatspolicyEntry
    MAX-ACCESS  not-accessible
    STATUS      obsolete
    DESCRIPTION 
        "The table that has all the policy stats for
         each  virtual service in NetScaler."
    ::= { cpestatistics 1 }

cpestatspolicyEntry OBJECT-TYPE
    SYNTAX      CpestatspolicyEntry
    MAX-ACCESS  not-accessible
    STATUS      obsolete
    DESCRIPTION 
        "The policy items for each entry."
    INDEX       { cpesDevno }
    ::= { cpestatspolicyTable 1 }

CpestatspolicyEntry ::= SEQUENCE {
    cpesDevno       Integer32,
    cpesPolicyname  OCTET STRING,
    cpesPolicyhits  Counter32
}

cpesDevno OBJECT-TYPE
    SYNTAX      Integer32
    MAX-ACCESS  read-only
    STATUS      obsolete
    DESCRIPTION 
        " The unique identifier for the policy"
    ::= { cpestatspolicyEntry 1 }

cpesPolicyname OBJECT-TYPE
    SYNTAX      OCTET STRING
    MAX-ACCESS  read-only
    STATUS      obsolete
    DESCRIPTION 
        " The name of the policy "
    ::= { cpestatspolicyEntry 2 }

cpesPolicyhits OBJECT-TYPE
    SYNTAX      Counter32
    MAX-ACCESS  read-only
    STATUS      obsolete
    DESCRIPTION 
        "Number of times that the policy condition has been met by NetScaler"
    ::= { cpestatspolicyEntry 3 }

cpestatsactionTable OBJECT-TYPE
    SYNTAX      SEQUENCE OF CpestatsactionEntry
    MAX-ACCESS  not-accessible
    STATUS      obsolete
    DESCRIPTION 
        "The table that has all the action stats for
         each  virtual service in NetScaler."
    ::= { cpestatistics 2 }

cpestatsactionEntry OBJECT-TYPE
    SYNTAX      CpestatsactionEntry
    MAX-ACCESS  not-accessible
    STATUS      obsolete
    DESCRIPTION 
        "The action items for each entry."
    INDEX       { cpeaDevno }
    ::= { cpestatsactionTable 1 }

CpestatsactionEntry ::= SEQUENCE {
    cpeaDevno       Integer32,
    actionname  OCTET STRING,
    actionhits  Counter32
}

cpeaDevno OBJECT-TYPE
    SYNTAX      Integer32
    MAX-ACCESS  read-only
    STATUS      obsolete
    DESCRIPTION 
        " The unique identifier for the action"
    ::= { cpestatsactionEntry 1 }

actionname OBJECT-TYPE
    SYNTAX      OCTET STRING
    MAX-ACCESS  read-only
    STATUS      obsolete
    DESCRIPTION 
        " The name of the action "
    ::= { cpestatsactionEntry 2 }

actionhits OBJECT-TYPE
    SYNTAX      Counter32
    MAX-ACCESS  read-only
    STATUS      obsolete
    DESCRIPTION 
        "Number of times that the action has been made by NetScaler"
    ::= { cpestatsactionEntry 3 }

cpeconfig OBJECT IDENTIFIER
    ::= { cpe 2 }

cpeconfigpolicyTable OBJECT-TYPE
    SYNTAX      SEQUENCE OF CpeconfigpolicyEntry
    MAX-ACCESS  not-accessible
    STATUS      obsolete
    DESCRIPTION 
        "The table that has all the policy stats for
         each  virtual service in NetScaler."
    ::= { cpeconfig 1 }

cpeconfigpolicyEntry OBJECT-TYPE
    SYNTAX      CpeconfigpolicyEntry
    MAX-ACCESS  not-accessible
    STATUS      obsolete
    DESCRIPTION 
        "The policy items for each entry."
    INDEX       { cpecDevno }
    ::= { cpeconfigpolicyTable 1 }

CpeconfigpolicyEntry ::= SEQUENCE {
    cpecDevno       Integer32,
    cpecPolicyname  OCTET STRING,
    reqrule     OCTET STRING,
    reqaction   OCTET STRING
}

cpecDevno OBJECT-TYPE
    SYNTAX      Integer32
    MAX-ACCESS  read-only
    STATUS      obsolete
    DESCRIPTION 
        " The unique identifier for the policy"
    ::= { cpeconfigpolicyEntry 1 }

cpecPolicyname OBJECT-TYPE
    SYNTAX      OCTET STRING
    MAX-ACCESS  read-only
    STATUS      obsolete
    DESCRIPTION 
        " The name of the policy "
    ::= { cpeconfigpolicyEntry 2 }

reqrule OBJECT-TYPE
    SYNTAX      OCTET STRING
    MAX-ACCESS  read-only
    STATUS      obsolete
    DESCRIPTION 
        "user defined request rule for the policy from client to NetScaler"
    ::= { cpeconfigpolicyEntry 3 }

reqaction OBJECT-TYPE
    SYNTAX      OCTET STRING
    MAX-ACCESS  read-only
    STATUS      obsolete
    DESCRIPTION 
        "user defined request action for the policy from client to NetScaler"
    ::= { cpeconfigpolicyEntry 4 }

cpeconfigactionTable OBJECT-TYPE
    SYNTAX      SEQUENCE OF CpeconfigactionEntry
    MAX-ACCESS  not-accessible
    STATUS      obsolete
    DESCRIPTION 
        "The table that has all the action configurations for
         each  virtual service in NetScaler."
    ::= { cpeconfig 2 }

cpeconfigactionEntry OBJECT-TYPE
    SYNTAX      CpeconfigactionEntry
    MAX-ACCESS  not-accessible
    STATUS      obsolete
    DESCRIPTION 
        "The action items for each entry."
    INDEX       { cpecaDevno }
    ::= { cpeconfigactionTable 1 }

CpeconfigactionEntry ::= SEQUENCE {
    cpecaDevno       Integer32,
    cpecaActionname  OCTET STRING,
    directive   INTEGER,
    qualifier   INTEGER,
    value       OCTET STRING,
    page        OCTET STRING,
    server      OCTET STRING
}

cpecaDevno OBJECT-TYPE
    SYNTAX      Integer32
    MAX-ACCESS  read-only
    STATUS      obsolete
    DESCRIPTION 
        " The unique identifier for the action"
    ::= { cpeconfigactionEntry 1 }

cpecaActionname OBJECT-TYPE
    SYNTAX      OCTET STRING
    MAX-ACCESS  read-only
    STATUS      obsolete
    DESCRIPTION 
        " The name of the action "
    ::= { cpeconfigactionEntry 2 }

directive OBJECT-TYPE
    SYNTAX      INTEGER { unknown(0), reset(1), drop(2), httpec(3), 
                    cmp(4), add(5), mod(6), del(7), cor(8), forward(9), 
                    noComparison(10), last(11) }
    MAX-ACCESS  read-only
    STATUS      obsolete
    DESCRIPTION 
        " The name of the directive associated with this action "
    ::= { cpeconfigactionEntry 3 }

qualifier OBJECT-TYPE
    SYNTAX      INTEGER { unknown(0), http(1), header(2), query(3) }
    MAX-ACCESS  read-only
    STATUS      obsolete
    DESCRIPTION 
        " The name of the qualifier associated with this action "
    ::= { cpeconfigactionEntry 4 }

value OBJECT-TYPE
    SYNTAX      OCTET STRING
    MAX-ACCESS  read-only
    STATUS      obsolete
    DESCRIPTION 
        " The value associated with this action . The value depends on 
         the directive . If the directive is RESPONSE , then the 
         value returned is status. Similarly , if the directive is
         either ADD or MOD or DEL , then the value returned is header.
         If the directive is RST or CMP, then NULL is returned"
    ::= { cpeconfigactionEntry 5 }

page OBJECT-TYPE
    SYNTAX      OCTET STRING
    MAX-ACCESS  read-only
    STATUS      obsolete
    DESCRIPTION 
        " The value of this depends on the value of directive. If value of
         directive is  RESPONSE  , then the page is returned, and if directive
         is MOD , then the header is returned , 
         otherwise NULL is returned"
    ::= { cpeconfigactionEntry 6 }

server OBJECT-TYPE
    SYNTAX      OCTET STRING
    MAX-ACCESS  read-only
    STATUS      obsolete
    DESCRIPTION 
        " The server name associated with this action based on the directive.
         If the directive is FORWARD , then the server returns the name of the
          service , otherwise returns empty string"
    ::= { cpeconfigactionEntry 7 }

cpeExprConfigStatsTable OBJECT-TYPE
    SYNTAX      SEQUENCE OF CpeExprConfigStatsEntry
    MAX-ACCESS  not-accessible
    STATUS      obsolete
    DESCRIPTION 
        "This table contains configuration information for each of 
         the expressions on the Netscaler   

	This Table is obsolete.Instead of this table use nsSysGroup.nsExpressionTable."
    ::= { cpe 3 }

cpeExprConfigStatsEntry OBJECT-TYPE
    SYNTAX      CpeExprConfigStatsEntry
    MAX-ACCESS  not-accessible
    STATUS      obsolete
    DESCRIPTION 
        "This table contains configuration information for each of 
         the expressions on the Netscaler   

	This Entry is obsolete.Instead of this entry use nsSysGroup.nsExpressionEntry."
    INDEX       { cpeeIndex }
    ::= { cpeExprConfigStatsTable 1 }

CpeExprConfigStatsEntry ::= SEQUENCE {
    cpeeIndex       Integer32,
    exprName    OCTET STRING,
    cpeeQualifier   INTEGER,
    operator    INTEGER,
    hdrName     OCTET STRING,
    cpeeValue       OCTET STRING,
    length      Integer32,
    offset      Integer32,
    cpeeNetmask     Integer32
}

cpeeIndex OBJECT-TYPE
    SYNTAX      Integer32
    MAX-ACCESS  read-only
    STATUS      obsolete
    DESCRIPTION 
        "The distinguishing Id for expression.

	This object is obsolete."
    ::= { cpeExprConfigStatsEntry 1 }

exprName OBJECT-TYPE
    SYNTAX      OCTET STRING
    MAX-ACCESS  read-only
    STATUS      obsolete
    DESCRIPTION 
        "The name of the expression.

	This object is obsolete.It can be measured through nsExpressionTable.expressionName."
    ::= { cpeExprConfigStatsEntry 2 }

cpeeQualifier OBJECT-TYPE
    SYNTAX      INTEGER { unknownQualifier(-1), method(0), 
                    urlPrefix(1), urlSuffix(2), urlTokens(3), 
                    version(4), header(5), urlQuery(6), url(7), 
                    urllen(8), urlquerylen(9), domain(10), sourceIp(11), 
                    sourcePort(12), destinationIp(13), 
                    destinationPort(14), compoundExpression(15), 
                    evaluatePredefined(16) }
    MAX-ACCESS  read-only
    STATUS      obsolete
    DESCRIPTION 
        "The qualifier of the expression."
    ::= { cpeExprConfigStatsEntry 3 }

operator OBJECT-TYPE
    SYNTAX      INTEGER { and(0), or(1), not(2), equal(3), notEqual(4), 
                    greaterThan(5), lessThan(6), 
                    greaterThanOrEqualTo(7), 
                    lessThanOrEqualTo(8), exists(9), notExists(10), 
                    contains(11), notContains(12), contents(13) }
    MAX-ACCESS  read-only
    STATUS      obsolete
    DESCRIPTION 
        "The operator in the expression."
    ::= { cpeExprConfigStatsEntry 4 }

hdrName OBJECT-TYPE
    SYNTAX      OCTET STRING
    MAX-ACCESS  read-only
    STATUS      obsolete
    DESCRIPTION 
        "The http header in the expression when the 
         value of qualifier is HEADER , otherwise empty string"
    ::= { cpeExprConfigStatsEntry 5 }

cpeeValue OBJECT-TYPE
    SYNTAX      OCTET STRING
    MAX-ACCESS  read-only
    STATUS      obsolete
    DESCRIPTION 
        "The value of the expression.

	This object is obsolete.It can be measured through nsExpressionTable.expressionValue."
    ::= { cpeExprConfigStatsEntry 6 }

length OBJECT-TYPE
    SYNTAX      Integer32
    MAX-ACCESS  read-only
    STATUS      obsolete
    DESCRIPTION 
        "The length , which is an optional value , used in 
         the expression . This has value only when the qualifier is
         CONTAINS or CONTENTS"
    ::= { cpeExprConfigStatsEntry 7 }

offset OBJECT-TYPE
    SYNTAX      Integer32
    MAX-ACCESS  read-only
    STATUS      obsolete
    DESCRIPTION 
        "The offset , which is an optional value , used in 
         the expression . This has value only when the qualifier is
         CONTAINS or CONTENTS"
    ::= { cpeExprConfigStatsEntry 8 }

cpeeNetmask OBJECT-TYPE
    SYNTAX      Integer32
    MAX-ACCESS  read-only
    STATUS      obsolete
    DESCRIPTION 
        "The netmask , which is an optional value , used in 
         the expression . This has value only when the qualifier is
         SOURCEIP"
    ::= { cpeExprConfigStatsEntry 9 }

EntityProtocolType ::=
	INTEGER{ http(0), ftp(1), tcp(2), udp(3), sslBridge(4), monitor(5), monitorUdp(6), nntp(7), httpserver(8), httpclient(9), rpcserver(10), rpcclient(11), nat(12), any(13), ssl(14), dns(15), adns(16), snmp(17), ha(18), monitorPing(19), sslOtherTcp(20), aaa(21), secureMonitor(22), sslvpnUdp(23), rip(24), dnsClient(25), rpcServer(26), rpcClient(27), dhcrpa(35), sipudp(38), dnstcp(42), adnstcp(43), rtsp(44), serviceUnknown(45) }

EntityState ::=
	INTEGER{ down(1), unknown(2), busy(3), outOfService(4), transitionToOutOfService(5), up(7), transitionToOutOfServiceDown(8) }

MepStatus ::=
	INTEGER{ mepInactive(5), mepActive(6), mepDown(7) }

SiteType ::=
	INTEGER{ localSite(1), remoteSite(2) }

MetricExchange ::=
	INTEGER{ disabled(3), enabled(4) }

AdminStatus ::=
	INTEGER{ disabled(1), enabled(2) }

HAMode ::=
	INTEGER{ standalone(0), primary(1), secondary(2), unknown(3) }

HAState ::=
	INTEGER{ unknown(0), init(1), down(2), up(3), partialFail(4), monitorFail(5), monitorOk(6), completeFail(7), dumb(8), disabled(9), partialFailSsl(10), routemonitorFail(11) }

HAON ::=
	INTEGER{ no(0), yes(1) }

FeatureStatus ::=
	INTEGER{ notLicensed(0), licensedButDisabled(1), licensedAndEnabled(2) }

FeaturePlatform ::=
	INTEGER{ ns(0), agee(1), nsva(2) }

ModeStatus ::=
	INTEGER{ disabled(0), enabled(1) }

LbPolicy ::=
	INTEGER{ weightedRoundRobin(1), leastConnections(2), leastResponse(3), asynchronousMAC(4), urlHashed(5), domainHashed(6), destinationIPHashed(7), sourceIPHashed(8), leastBandwidth(9), leastPackets(10), customLoad(11), token(12), staticProximity(13), rtt(14), sourceIPDestinationIPHashed(15), sourceIPSourcePort(16), lrtm(17), callIDHashed(18) }

PersistanceType ::=
	INTEGER{ none(0), sourceIp(1), cookieInsert(2), cookieDelete(3), cookieRead(4), cookieHash(5), sessionId(6), server(7), rule(8), urlPassive(9), customServerID(10), groupSourceID(11), groupCookieInsert(12), destinationIP(13), spillOver(14), sourceIPdestinationIP(15), callerID(16), gslbBackup(17), rtspSessionID(18) }

ActionType ::=
	INTEGER{ ns(1), acs(2), noAction(3) }

InputFormat ::=
	INTEGER{ der(1), pem(3) }

IpAddressType ::=
	INTEGER{ netScalerIp(1), mappedIp(2), subnetIp(4) }

IpAddressMode ::=
	INTEGER{ active(1), passive(2) }

AuthorizationStatus ::=
	INTEGER{ authorized(1), notAuthorized(2) }

CommandExecutionStatus ::=
	INTEGER{ failed(1), successful(2) }

MonitorType ::=
	INTEGER{ ping(1), tcp(2), http(3), tcpEcv(4), httpEcv(5), udpEcv(6), dns(7), ftp(8), https(9), tcps(10), ldnsPing(11), ldnsTcp(12), ldnsDns(13), radius(14), dbsResolver(15), user(16), httpInline(17), sipUdp(18), sipTcp(19) }

MonitorState ::=
	INTEGER{ monitorStateDown(1), monitorStateUnknown(2), monitorStateUp(7) }

ServiceGroupState ::=
	INTEGER{ disabled(0), enabled(1) }

VServerType ::=
	INTEGER{ unknown(0), loadbalancing(1), loadbalancinggroup(2), sslvpn(3), contentswitching(4), cacheredirection(5) }

SvcEntityType ::=
	INTEGER{ service(0), serviceGroupMember(1) }

nsProducts OBJECT IDENTIFIER
	::= { netScaler 4 }

rs9000 OBJECT IDENTIFIER
	::= { nsProducts 1 }

nsSysGroup OBJECT IDENTIFIER
	::= { rs9000 1 }

sysBuildVersion  OBJECT-TYPE
	SYNTAX  OCTET STRING
	MAX-ACCESS  read-only
	STATUS  current
	DESCRIPTION
		"This shows the version of the kernel build running on the netscaler."
	::= { nsSysGroup 1 }

sysIpAddress  OBJECT-TYPE
	SYNTAX  IpAddress
	MAX-ACCESS  read-only
	STATUS  current
	DESCRIPTION
		"This shows the configured ipaddress of the NetScaler"
	::= { nsSysGroup 2 }

sysNetmask  OBJECT-TYPE
	SYNTAX  IpAddress
	MAX-ACCESS  read-only
	STATUS  current
	DESCRIPTION
		"This shows the configured netmask of the NetScaler"
	::= { nsSysGroup 3 }

sysMappedIpAddress  OBJECT-TYPE
	SYNTAX  IpAddress
	MAX-ACCESS  read-only
	STATUS  obsolete
	DESCRIPTION
		"...OBSOLETE"
	::= { nsSysGroup 4 }

sysMappedIpAddressRange  OBJECT-TYPE
	SYNTAX  Integer32
	MAX-ACCESS  read-only
	STATUS  obsolete
	DESCRIPTION
		"...OBSOLETE"
	::= { nsSysGroup 5 }

sysHighAvailabilityMode  OBJECT-TYPE
	SYNTAX  HAMode
	MAX-ACCESS  read-only
	STATUS  current
	DESCRIPTION
		"This shows whether NetScaler is in standalone mode or whether it is primary or secondary in case of failover mode."
	::= { nsSysGroup 6 }

sysGateway  OBJECT-TYPE
	SYNTAX  IpAddress
	MAX-ACCESS  read-only
	STATUS  current
	DESCRIPTION
		"This represents the default gateway configured on the NetScaler"
	::= { nsSysGroup 7 }

sysCurMappedIpCount  OBJECT-TYPE
	SYNTAX  Gauge32
	MAX-ACCESS  read-only
	STATUS  current
	DESCRIPTION
		"This represents the number of Mapped IPs currently configured on the NetScaler system"
	::= { nsSysGroup 8 }

sysCustomID  OBJECT-TYPE
	SYNTAX  OCTET STRING
	MAX-ACCESS  read-only
	STATUS  current
	DESCRIPTION
		"Configurable Identifier for the system"
	::= { nsSysGroup 9 }

sysHardwareVersionId  OBJECT-TYPE
	SYNTAX  Integer32
	MAX-ACCESS  read-only
	STATUS  current
	DESCRIPTION
		"The hardware version ID of the NetScaler system"
	::= { nsSysGroup 10 }

sysHardwareVersionDesc  OBJECT-TYPE
	SYNTAX  OCTET STRING
	MAX-ACCESS  read-only
	STATUS  current
	DESCRIPTION
		"The hardware version description of the NetScaler system"
	::= { nsSysGroup 11 }

sysTotConfigChanges  OBJECT-TYPE
	SYNTAX  Counter64
	MAX-ACCESS  read-only
	STATUS  current
	DESCRIPTION
		"The number of times a configuration change was made on the NetScaler"
	::= { nsSysGroup 12 }

sysTotSaveConfigs  OBJECT-TYPE
	SYNTAX  Counter64
	MAX-ACCESS  read-only
	STATUS  current
	DESCRIPTION
		"The number of times config was saved"
	::= { nsSysGroup 13 }

sysHardwareSerialNumber  OBJECT-TYPE
	SYNTAX  OCTET STRING
	MAX-ACCESS  read-only
	STATUS  current
	DESCRIPTION
		"The serial number of the NetScaler system."
	::= { nsSysGroup 14 }

sysHardwareEncodedSerialNumber  OBJECT-TYPE
	SYNTAX  OCTET STRING
	MAX-ACCESS  read-only
	STATUS  current
	DESCRIPTION
		"The encoded serial no of the NetScaler system."
	::= { nsSysGroup 15 }

nsFeatureInfo OBJECT IDENTIFIER
	::= { nsSysGroup 20 }

featureWebLogging  OBJECT-TYPE
	SYNTAX  FeatureStatus
	MAX-ACCESS  read-only
	STATUS  current
	DESCRIPTION
		"This represents whether webLogging feature is enabled or disabled on NetScaler."
	::= { nsFeatureInfo 1 }

featureSurgeProtection  OBJECT-TYPE
	SYNTAX  FeatureStatus
	MAX-ACCESS  read-only
	STATUS  current
	DESCRIPTION
		"This represents whether surgeProtection feature is enabled or disabled on NetScaler."
	::= { nsFeatureInfo 2 }

featureLoadBalancing  OBJECT-TYPE
	SYNTAX  FeatureStatus
	MAX-ACCESS  read-only
	STATUS  current
	DESCRIPTION
		"This represents whether LoadBalancing feature is enabled or disabled on NetScaler."
	::= { nsFeatureInfo 3 }

featureContentSwitching  OBJECT-TYPE
	SYNTAX  FeatureStatus
	MAX-ACCESS  read-only
	STATUS  current
	DESCRIPTION
		"This represents whether contentSwitching feature is enabled or disabled on NetScaler."
	::= { nsFeatureInfo 4 }

featureCacheRedirection  OBJECT-TYPE
	SYNTAX  FeatureStatus
	MAX-ACCESS  read-only
	STATUS  current
	DESCRIPTION
		"This represents whether cacheRedirection feature is enabled or disabled on NetScaler."
	::= { nsFeatureInfo 5 }

featureSureConnect  OBJECT-TYPE
	SYNTAX  FeatureStatus
	MAX-ACCESS  read-only
	STATUS  current
	DESCRIPTION
		"This represents whether sureConnect feature is enabled or disabled on NetScaler."
	::= { nsFeatureInfo 6 }

featureCompression  OBJECT-TYPE
	SYNTAX  FeatureStatus
	MAX-ACCESS  read-only
	STATUS  current
	DESCRIPTION
		"This represents whether compression feature is enabled or disabled on NetScaler."
	::= { nsFeatureInfo 7 }

featurePriorityQueuing  OBJECT-TYPE
	SYNTAX  FeatureStatus
	MAX-ACCESS  read-only
	STATUS  current
	DESCRIPTION
		"This represents whether priorityQueuing feature is enabled or disabled on NetScaler."
	::= { nsFeatureInfo 8 }

featureSslOffloading  OBJECT-TYPE
	SYNTAX  FeatureStatus
	MAX-ACCESS  read-only
	STATUS  current
	DESCRIPTION
		"This represents whether sslOffloading feature is enabled or disabled on NetScaler."
	::= { nsFeatureInfo 9 }

featureGslb  OBJECT-TYPE
	SYNTAX  FeatureStatus
	MAX-ACCESS  read-only
	STATUS  current
	DESCRIPTION
		"This represents whether gslb feature is enabled or disabled on NetScaler."
	::= { nsFeatureInfo 10 }

featureHttpDosProtection  OBJECT-TYPE
	SYNTAX  FeatureStatus
	MAX-ACCESS  read-only
	STATUS  current
	DESCRIPTION
		"This represents whether httpDosProtection feature is enabled or disabled on NetScaler."
	::= { nsFeatureInfo 11 }

featureDynamicRouting  OBJECT-TYPE
	SYNTAX  FeatureStatus
	MAX-ACCESS  read-only
	STATUS  obsolete
	DESCRIPTION
		"...OBSOLETE"
	::= { nsFeatureInfo 12 }

featureContentFiltering  OBJECT-TYPE
	SYNTAX  FeatureStatus
	MAX-ACCESS  read-only
	STATUS  current
	DESCRIPTION
		"This represents whether contentFiltering feature is enabled or disabled on NetScaler."
	::= { nsFeatureInfo 13 }

featureInternalCaching  OBJECT-TYPE
	SYNTAX  FeatureStatus
	MAX-ACCESS  read-only
	STATUS  current
	DESCRIPTION
		"This represents whether internalCaching feature is enabled or disabled on NetScaler."
	::= { nsFeatureInfo 14 }

featureSSLVPN  OBJECT-TYPE
	SYNTAX  FeatureStatus
	MAX-ACCESS  read-only
	STATUS  current
	DESCRIPTION
		"This represents whether SSL VPN feature is enabled or disabled on NetScaler."
	::= { nsFeatureInfo 15 }

featureOSPF  OBJECT-TYPE
	SYNTAX  FeatureStatus
	MAX-ACCESS  read-only
	STATUS  current
	DESCRIPTION
		"This represents whether OSPF feature is enabled or disabled on NetScaler."
	::= { nsFeatureInfo 16 }

featureRIP  OBJECT-TYPE
	SYNTAX  FeatureStatus
	MAX-ACCESS  read-only
	STATUS  current
	DESCRIPTION
		"This represents whether RIP feature is enabled or disabled on NetScaler."
	::= { nsFeatureInfo 17 }

featureBGP  OBJECT-TYPE
	SYNTAX  FeatureStatus
	MAX-ACCESS  read-only
	STATUS  current
	DESCRIPTION
		"This represents whether BGP feature is enabled or disabled on NetScaler."
	::= { nsFeatureInfo 18 }

featureRewrite  OBJECT-TYPE
	SYNTAX  FeatureStatus
	MAX-ACCESS  read-only
	STATUS  current
	DESCRIPTION
		"This represents whether Rewrite feature is enabled or disabled on NetScaler."
	::= { nsFeatureInfo 19 }

featureDeltaCompression  OBJECT-TYPE
	SYNTAX  FeatureStatus
	MAX-ACCESS  read-only
	STATUS  current
	DESCRIPTION
		"This represents whether Delta Compression feature is enabled or disabled on NetScaler."
	::= { nsFeatureInfo 20 }

featureGSLBProximity  OBJECT-TYPE
	SYNTAX  FeatureStatus
	MAX-ACCESS  read-only
	STATUS  current
	DESCRIPTION
		"This represents whether GSLB Proximity feature is enabled or disabled on NetScaler."
	::= { nsFeatureInfo 21 }

featureIPv6ProtocolTranslation  OBJECT-TYPE
	SYNTAX  FeatureStatus
	MAX-ACCESS  read-only
	STATUS  current
	DESCRIPTION
		"This represents whether IPv6 Protocol Translation feature is enabled or disabled on NetScaler."
	::= { nsFeatureInfo 22 }

featureApplicationFirewall  OBJECT-TYPE
	SYNTAX  FeatureStatus
	MAX-ACCESS  read-only
	STATUS  current
	DESCRIPTION
		"This represents whether Application Firewall feature is enabled or disabled on NetScaler."
	::= { nsFeatureInfo 23 }

featureResponder  OBJECT-TYPE
	SYNTAX  FeatureStatus
	MAX-ACCESS  read-only
	STATUS  current
	DESCRIPTION
		"This represents whether Responder feature is enabled or disabled on NetScaler."
	::= { nsFeatureInfo 24 }

featureHtmlInjection  OBJECT-TYPE
	SYNTAX  FeatureStatus
	MAX-ACCESS  read-only
	STATUS  current
	DESCRIPTION
		"This represents whether Html Injection feature is enabled or disabled on Netscaler."
	::= { nsFeatureInfo 25 }

featureAAA  OBJECT-TYPE
	SYNTAX  FeatureStatus
	MAX-ACCESS  read-only
	STATUS  current
	DESCRIPTION
		"This represents whether Authentication, Authorization and Auditing features for Traffic Management vservers are enabled or disabled on NetScaler."
	::= { nsFeatureInfo 26 }

featureAGEE  OBJECT-TYPE
	SYNTAX  FeatureStatus
	MAX-ACCESS  read-only
	STATUS  current
	DESCRIPTION
		"This represents whether AGEE feature of SSLVPN is enabled or disabled on Netscaler."
	::= { nsFeatureInfo 50 }

featurePLATFORM  OBJECT-TYPE
	SYNTAX  FeaturePlatform
	MAX-ACCESS  read-only
	STATUS  current
	DESCRIPTION
		"This gives platform information AGEE 1 NSVA 2 etc"
	::= { nsFeatureInfo 60 }

nsModeInfo OBJECT IDENTIFIER
	::= { nsSysGroup 21 }

modeFastRamp  OBJECT-TYPE
	SYNTAX  ModeStatus
	MAX-ACCESS  read-only
	STATUS  current
	DESCRIPTION
		"This represents whether fastRamp mode is enabled or disabled on NetScaler."
	::= { nsModeInfo 1 }

l2Mode  OBJECT-TYPE
	SYNTAX  ModeStatus
	MAX-ACCESS  read-only
	STATUS  current
	DESCRIPTION
		"This represents whether l2Mode mode is enabled or disabled on NetScaler."
	::= { nsModeInfo 2 }

modeUseSrcIp  OBJECT-TYPE
	SYNTAX  ModeStatus
	MAX-ACCESS  read-only
	STATUS  current
	DESCRIPTION
		"This represents whether useSrcIp mode is enabled or disabled on NetScaler."
	::= { nsModeInfo 3 }

modeClientKeepAlive  OBJECT-TYPE
	SYNTAX  ModeStatus
	MAX-ACCESS  read-only
	STATUS  current
	DESCRIPTION
		"This represents whether clientKeepAlive mode is enabled or disabled on NetScaler."
	::= { nsModeInfo 4 }

modeTcpBuffering  OBJECT-TYPE
	SYNTAX  ModeStatus
	MAX-ACCESS  read-only
	STATUS  current
	DESCRIPTION
		"This represents whether tcpBuffering mode is enabled or disabled on NetScaler."
	::= { nsModeInfo 5 }

modeMacBasedForwarding  OBJECT-TYPE
	SYNTAX  ModeStatus
	MAX-ACCESS  read-only
	STATUS  current
	DESCRIPTION
		"This represents whether macBasedForwarding mode is enabled or disabled on NetScaler."
	::= { nsModeInfo 6 }

modeUseSubnetIp  OBJECT-TYPE
	SYNTAX  ModeStatus
	MAX-ACCESS  read-only
	STATUS  current
	DESCRIPTION
		"This represents whether Use Subnet IP mode is enabled or disabled on NetScaler."
	::= { nsModeInfo 7 }

modeEdgeConfiguration  OBJECT-TYPE
	SYNTAX  ModeStatus
	MAX-ACCESS  read-only
	STATUS  current
	DESCRIPTION
		"This represents whether Edge Configuration mode is enabled or disabled on NetScaler."
	::= { nsModeInfo 8 }

l3mode  OBJECT-TYPE
	SYNTAX  ModeStatus
	MAX-ACCESS  read-only
	STATUS  current
	DESCRIPTION
		"This represents whether l3 mode (ip forwarding) is enabled or disabled on NetScaler."
	::= { nsModeInfo 9 }

modePathMTUDiscovery  OBJECT-TYPE
	SYNTAX  ModeStatus
	MAX-ACCESS  read-only
	STATUS  current
	DESCRIPTION
		"This represents whether path MTU discovery mode is enabled or disabled on NetScaler."
	::= { nsModeInfo 10 }

modeStaticRouteAdv  OBJECT-TYPE
	SYNTAX  ModeStatus
	MAX-ACCESS  read-only
	STATUS  current
	DESCRIPTION
		"This represents whether static route advertisement mode is enabled or disabled on NetScaler."
	::= { nsModeInfo 11 }

modeDirectRouteAdv  OBJECT-TYPE
	SYNTAX  ModeStatus
	MAX-ACCESS  read-only
	STATUS  current
	DESCRIPTION
		"This represents whether direct route advertisement mode is enabled or disabled on NetScaler."
	::= { nsModeInfo 12 }

modeIntranetRouteAdv  OBJECT-TYPE
	SYNTAX  ModeStatus
	MAX-ACCESS  read-only
	STATUS  current
	DESCRIPTION
		"This represents whether intranet route advertisement mode is enabled or disabled on NetScaler."
	::= { nsModeInfo 13 }

modeIpv6StaticRouteAdv  OBJECT-TYPE
	SYNTAX  ModeStatus
	MAX-ACCESS  read-only
	STATUS  current
	DESCRIPTION
		"This represents whether Ipv6 static route advertisement mode is enabled or disabled on NetScaler."
	::= { nsModeInfo 14 }

modeIpv6DirectRouteAdv  OBJECT-TYPE
	SYNTAX  ModeStatus
	MAX-ACCESS  read-only
	STATUS  current
	DESCRIPTION
		"This represents whether Ipv6 direct route advertisement mode is enabled or disabled on NetScaler."
	::= { nsModeInfo 15 }

brgBpdu  OBJECT-TYPE
	SYNTAX  ModeStatus
	MAX-ACCESS  read-only
	STATUS  current
	DESCRIPTION
		"This represents whether Bridging of BPDU is enabled or disabled on NetScaler."
	::= { nsModeInfo 16 }

nsFiltersGroup OBJECT IDENTIFIER
	::= { nsSysGroup 22 }

aclStatsGroup OBJECT IDENTIFIER
	::= { nsFiltersGroup 1 }

aclTotPktsBridgedLow  OBJECT-TYPE
	SYNTAX  Counter32
	MAX-ACCESS  read-only
	STATUS  obsolete
	DESCRIPTION
		"...OBSOLETE"
	::= { aclStatsGroup 1 }

aclTotPktsBridgedHigh  OBJECT-TYPE
	SYNTAX  Counter32
	MAX-ACCESS  read-only
	STATUS  obsolete
	DESCRIPTION
		"...OBSOLETE"
	::= { aclStatsGroup 2 }

aclTotPktsDeniedLow  OBJECT-TYPE
	SYNTAX  Counter32
	MAX-ACCESS  read-only
	STATUS  obsolete
	DESCRIPTION
		"...OBSOLETE"
	::= { aclStatsGroup 3 }

aclTotPktsDeniedHigh  OBJECT-TYPE
	SYNTAX  Counter32
	MAX-ACCESS  read-only
	STATUS  obsolete
	DESCRIPTION
		"...OBSOLETE"
	::= { aclStatsGroup 4 }

aclTotPktsAllowedLow  OBJECT-TYPE
	SYNTAX  Counter32
	MAX-ACCESS  read-only
	STATUS  obsolete
	DESCRIPTION
		"...OBSOLETE"
	::= { aclStatsGroup 5 }

aclTotPktsAllowedHigh  OBJECT-TYPE
	SYNTAX  Counter32
	MAX-ACCESS  read-only
	STATUS  obsolete
	DESCRIPTION
		"...OBSOLETE"
	::= { aclStatsGroup 6 }

aclTotPktsReusedLow  OBJECT-TYPE
	SYNTAX  Counter32
	MAX-ACCESS  read-only
	STATUS  obsolete
	DESCRIPTION
		"...OBSOLETE"
	::= { aclStatsGroup 7 }

aclTotPktsReusedHigh  OBJECT-TYPE
	SYNTAX  Counter32
	MAX-ACCESS  read-only
	STATUS  obsolete
	DESCRIPTION
		"...OBSOLETE"
	::= { aclStatsGroup 8 }

aclTotPktsBridged  OBJECT-TYPE
	SYNTAX  Counter64
	MAX-ACCESS  read-only
	STATUS  current
	DESCRIPTION
		"Packets matching a bridge ACL, which in transparent mode bypasses service processing."
	::= { aclStatsGroup 9 }

aclTotPktsDenied  OBJECT-TYPE
	SYNTAX  Counter64
	MAX-ACCESS  read-only
	STATUS  current
	DESCRIPTION
		"Packets dropped because they match ACLs with processing mode set to DENY."
	::= { aclStatsGroup 10 }

aclTotPktsAllowed  OBJECT-TYPE
	SYNTAX  Counter64
	MAX-ACCESS  read-only
	STATUS  current
	DESCRIPTION
		"Packets matching ACLs with processing mode set to ALLOW. NetScaler processes these packets."
	::= { aclStatsGroup 11 }

aclTotHits  OBJECT-TYPE
	SYNTAX  Counter64
	MAX-ACCESS  read-only
	STATUS  current
	DESCRIPTION
		"Packets matching an ACL."
	::= { aclStatsGroup 12 }

aclTotMisses  OBJECT-TYPE
	SYNTAX  Counter64
	MAX-ACCESS  read-only
	STATUS  current
	DESCRIPTION
		"Packets not matching any ACL."
	::= { aclStatsGroup 13 }

aclTotPktsNAT  OBJECT-TYPE
	SYNTAX  Counter64
	MAX-ACCESS  read-only
	STATUS  current
	DESCRIPTION
		"Packets matching a NAT ACL, resulting in a NAT session."
	::= { aclStatsGroup 14 }

nsAclTable  OBJECT-TYPE
	SYNTAX  SEQUENCE OF NsAclEntry
	MAX-ACCESS  not-accessible
	STATUS  current
	DESCRIPTION
		"This table contains all the ACLs configured"
	::= { aclStatsGroup 20 }

nsAclEntry  OBJECT-TYPE
	SYNTAX  NsAclEntry
	MAX-ACCESS  not-accessible
	STATUS  current
	DESCRIPTION
		"..."
	INDEX { aclName   }
	::= { nsAclTable 1 }

NsAclEntry ::= SEQUENCE {
	aclName  OCTET STRING,
	aclPriority  Integer32,
	aclHits  Counter64,
	aclperHits  Counter64
}

aclName  OBJECT-TYPE
	SYNTAX  OCTET STRING
	MAX-ACCESS  read-only
	STATUS  current
	DESCRIPTION
		"The name of the ACL"
	::= { nsAclEntry 1 }

aclPriority  OBJECT-TYPE
	SYNTAX  Integer32
	MAX-ACCESS  read-only
	STATUS  current
	DESCRIPTION
		"The priority of the ACL"
	::= { nsAclEntry 2 }

aclHits  OBJECT-TYPE
	SYNTAX  Counter64
	MAX-ACCESS  read-only
	STATUS  obsolete
	DESCRIPTION
		"...OBSOLETE"
	::= { nsAclEntry 3 }

aclperHits  OBJECT-TYPE
	SYNTAX  Counter64
	MAX-ACCESS  read-only
	STATUS  current
	DESCRIPTION
		"Number of times the acl was hit"
	::= { nsAclEntry 4 }

contentFiltersTable  OBJECT-TYPE
	SYNTAX  SEQUENCE OF ContentFiltersEntry
	MAX-ACCESS  not-accessible
	STATUS  obsolete
	DESCRIPTION
		"...OBSOLETE"
	::= { nsFiltersGroup 2 }

contentFiltersEntry  OBJECT-TYPE
	SYNTAX  ContentFiltersEntry
	MAX-ACCESS  not-accessible
	STATUS  obsolete
	DESCRIPTION
		"...OBSOLETE"
	INDEX { contentFilterName   }
	::= { contentFiltersTable 1 }

ContentFiltersEntry ::= SEQUENCE {
	contentFilterName  OCTET STRING,
	contentFilterHitsLow  Counter32,
	contentFilterHitsHigh  Counter32,
	contentFilterHits  Counter64
}

contentFilterName  OBJECT-TYPE
	SYNTAX  OCTET STRING
	MAX-ACCESS  read-only
	STATUS  obsolete
	DESCRIPTION
		"...OBSOLETE"
	::= { contentFiltersEntry 1 }

contentFilterHitsLow  OBJECT-TYPE
	SYNTAX  Counter32
	MAX-ACCESS  read-only
	STATUS  obsolete
	DESCRIPTION
		"...OBSOLETE"
	::= { contentFiltersEntry 2 }

contentFilterHitsHigh  OBJECT-TYPE
	SYNTAX  Counter32
	MAX-ACCESS  read-only
	STATUS  obsolete
	DESCRIPTION
		"...OBSOLETE"
	::= { contentFiltersEntry 3 }

contentFilterHits  OBJECT-TYPE
	SYNTAX  Counter64
	MAX-ACCESS  read-only
	STATUS  obsolete
	DESCRIPTION
		"...OBSOLETE"
	::= { contentFiltersEntry 4 }

acl6StatsGroup OBJECT IDENTIFIER
	::= { nsFiltersGroup 3 }

acl6TotPktsBridgedLow  OBJECT-TYPE
	SYNTAX  Counter32
	MAX-ACCESS  read-only
	STATUS  obsolete
	DESCRIPTION
		"...OBSOLETE"
	::= { acl6StatsGroup 1 }

acl6TotPktsBridgedHigh  OBJECT-TYPE
	SYNTAX  Counter32
	MAX-ACCESS  read-only
	STATUS  obsolete
	DESCRIPTION
		"...OBSOLETE"
	::= { acl6StatsGroup 2 }

acl6TotPktsDeniedLow  OBJECT-TYPE
	SYNTAX  Counter32
	MAX-ACCESS  read-only
	STATUS  obsolete
	DESCRIPTION
		"...OBSOLETE"
	::= { acl6StatsGroup 3 }

acl6TotPktsDeniedHigh  OBJECT-TYPE
	SYNTAX  Counter32
	MAX-ACCESS  read-only
	STATUS  obsolete
	DESCRIPTION
		"...OBSOLETE"
	::= { acl6StatsGroup 4 }

acl6TotPktsAllowedLow  OBJECT-TYPE
	SYNTAX  Counter32
	MAX-ACCESS  read-only
	STATUS  obsolete
	DESCRIPTION
		"...OBSOLETE"
	::= { acl6StatsGroup 5 }

acl6TotPktsAllowedHigh  OBJECT-TYPE
	SYNTAX  Counter32
	MAX-ACCESS  read-only
	STATUS  obsolete
	DESCRIPTION
		"...OBSOLETE"
	::= { acl6StatsGroup 6 }

acl6TotPktsReusedLow  OBJECT-TYPE
	SYNTAX  Counter32
	MAX-ACCESS  read-only
	STATUS  obsolete
	DESCRIPTION
		"...OBSOLETE"
	::= { acl6StatsGroup 7 }

acl6TotPktsReusedHigh  OBJECT-TYPE
	SYNTAX  Counter32
	MAX-ACCESS  read-only
	STATUS  obsolete
	DESCRIPTION
		"...OBSOLETE"
	::= { acl6StatsGroup 8 }

acl6TotPktsBridged  OBJECT-TYPE
	SYNTAX  Counter64
	MAX-ACCESS  read-only
	STATUS  current
	DESCRIPTION
		"Packets matching a bridge IPv6 ACL, which in transparent mode bypasses service processing."
	::= { acl6StatsGroup 9 }

acl6TotPktsDenied  OBJECT-TYPE
	SYNTAX  Counter64
	MAX-ACCESS  read-only
	STATUS  current
	DESCRIPTION
		"Packets dropped because they match IPv6 ACLs with processing mode set to DENY."
	::= { acl6StatsGroup 10 }

acl6TotPktsAllowed  OBJECT-TYPE
	SYNTAX  Counter64
	MAX-ACCESS  read-only
	STATUS  current
	DESCRIPTION
		"Packets matching IPv6 ACLs with processing mode set to ALLOW. NetScaler processes these packets."
	::= { acl6StatsGroup 11 }

acl6TotHits  OBJECT-TYPE
	SYNTAX  Counter64
	MAX-ACCESS  read-only
	STATUS  current
	DESCRIPTION
		"Packets matching an IPv6 ACL."
	::= { acl6StatsGroup 12 }

acl6TotMisses  OBJECT-TYPE
	SYNTAX  Counter64
	MAX-ACCESS  read-only
	STATUS  current
	DESCRIPTION
		"Packets not matching any IPv6 ACL."
	::= { acl6StatsGroup 13 }

acl6TotPktsNAT  OBJECT-TYPE
	SYNTAX  Counter64
	MAX-ACCESS  read-only
	STATUS  current
	DESCRIPTION
		"Packets matching a NAT ACL6, resulting in a NAT session."
	::= { acl6StatsGroup 14 }

nsAcl6Table  OBJECT-TYPE
	SYNTAX  SEQUENCE OF NsAcl6Entry
	MAX-ACCESS  not-accessible
	STATUS  current
	DESCRIPTION
		"This table contains all the ACLs6 configured"
	::= { acl6StatsGroup 20 }

nsAcl6Entry  OBJECT-TYPE
	SYNTAX  NsAcl6Entry
	MAX-ACCESS  not-accessible
	STATUS  current
	DESCRIPTION
		"..."
	INDEX { acAclName   }
	::= { nsAcl6Table 1 }

NsAcl6Entry ::= SEQUENCE {
	acl6Name  OCTET STRING,
	acl6Priority  Integer32,
	acl6Hits  Counter64,
	acAclName  OCTET STRING,
	acl6perHits  Counter64
}

acl6Name  OBJECT-TYPE
	SYNTAX  OCTET STRING
	MAX-ACCESS  read-only
	STATUS  obsolete
	DESCRIPTION
		"...OBSOLETE"
	::= { nsAcl6Entry 1 }

acl6Priority  OBJECT-TYPE
	SYNTAX  Integer32
	MAX-ACCESS  read-only
	STATUS  current
	DESCRIPTION
		"The priority of the ACL6"
	::= { nsAcl6Entry 2 }

acl6Hits  OBJECT-TYPE
	SYNTAX  Counter64
	MAX-ACCESS  read-only
	STATUS  obsolete
	DESCRIPTION
		"...OBSOLETE"
	::= { nsAcl6Entry 3 }

acAclName  OBJECT-TYPE
	SYNTAX  OCTET STRING
	MAX-ACCESS  read-only
	STATUS  current
	DESCRIPTION
		"The name of the ACL6"
	::= { nsAcl6Entry 4 }

acl6perHits  OBJECT-TYPE
	SYNTAX  Counter64
	MAX-ACCESS  read-only
	STATUS  current
	DESCRIPTION
		"Number of times the acl6 was hit"
	::= { nsAcl6Entry 5 }

saclStatsGroup OBJECT IDENTIFIER
	::= { nsFiltersGroup 4 }

saclTotPktsBridged  OBJECT-TYPE
	SYNTAX  Counter64
	MAX-ACCESS  read-only
	STATUS  current
	DESCRIPTION
		"Total packets that matched a SimpleACL with action BRIDGE and got bridged by NetScaler."
	::= { saclStatsGroup 1 }

saclTotPktsDenied  OBJECT-TYPE
	SYNTAX  Counter64
	MAX-ACCESS  read-only
	STATUS  current
	DESCRIPTION
		"Packets dropped because they match deny simple ACL."
	::= { saclStatsGroup 2 }

saclTotPktsAllowed  OBJECT-TYPE
	SYNTAX  Counter64
	MAX-ACCESS  read-only
	STATUS  current
	DESCRIPTION
		"Total packets that matched a SimpleACL with action ALLOW and got consumed by NetScaler."
	::= { saclStatsGroup 3 }

saclTotHits  OBJECT-TYPE
	SYNTAX  Counter64
	MAX-ACCESS  read-only
	STATUS  current
	DESCRIPTION
		"Packets matching a simple ACL."
	::= { saclStatsGroup 4 }

saclTotMisses  OBJECT-TYPE
	SYNTAX  Counter64
	MAX-ACCESS  read-only
	STATUS  current
	DESCRIPTION
		"Packets not matching any simple ACL."
	::= { saclStatsGroup 5 }

saclsCount  OBJECT-TYPE
	SYNTAX  Counter64
	MAX-ACCESS  read-only
	STATUS  current
	DESCRIPTION
		"Number of simple ACLs configured."
	::= { saclStatsGroup 6 }

nsHighAvailabilityGroup OBJECT IDENTIFIER
	::= { nsSysGroup 23 }

haPeerId  OBJECT-TYPE
	SYNTAX  Integer32
	MAX-ACCESS  read-only
	STATUS  current
	DESCRIPTION
		"The unique identifier to represent the failover peer NetScaler"
	::= { nsHighAvailabilityGroup 1 }

haPeerIpAddress  OBJECT-TYPE
	SYNTAX  IpAddress
	MAX-ACCESS  read-only
	STATUS  current
	DESCRIPTION
		"This represents the ipaddress of the failover peer NetScaler"
	::= { nsHighAvailabilityGroup 2 }

haPeerState  OBJECT-TYPE
	SYNTAX  HAMode
	MAX-ACCESS  read-only
	STATUS  current
	DESCRIPTION
		"This represents the state of the failover peer NetScaler whether Primary or Secondary"
	::= { nsHighAvailabilityGroup 3 }

haTotStateTransitions  OBJECT-TYPE
	SYNTAX  Counter64
	MAX-ACCESS  read-only
	STATUS  current
	DESCRIPTION
		"This represents the total number of master state changes that the NetScaler has made from primary to secondary and vice-versa"
	::= { nsHighAvailabilityGroup 4 }

haTimeofLastStateTransition  OBJECT-TYPE
	SYNTAX  TimeTicks
	MAX-ACCESS  read-only
	STATUS  current
	DESCRIPTION
		"This represents the time since the NetScaler underwent a state change from primary to secondary or vice-versa"
	::= { nsHighAvailabilityGroup 5 }

haTotStateFail  OBJECT-TYPE
	SYNTAX  Counter64
	MAX-ACCESS  read-only
	STATUS  current
	DESCRIPTION
		"Number of times state changed to PARTIAL_FAIL/PARTIAL_FAIL_SSL/ROUTEMONITOR_FAIL/COMPLETE_FAIL"
	::= { nsHighAvailabilityGroup 6 }

haErrSyncFailure  OBJECT-TYPE
	SYNTAX  Counter64
	MAX-ACCESS  read-only
	STATUS  current
	DESCRIPTION
		"Number of times the configuration of the primary and secondary nodes failed to synchronize since that last transition. A synchronization failure results in mismatched configuration. It can be caused by a mismatch in the Remote Procedural Call (RPC) password on the two nodes forming the high availability pair."
	::= { nsHighAvailabilityGroup 7 }

haErrTotNodeDown  OBJECT-TYPE
	SYNTAX  Counter64
	MAX-ACCESS  read-only
	STATUS  current
	DESCRIPTION
		"Total number of heart-beats missed while the peer node is DOWN."
	::= { nsHighAvailabilityGroup 8 }

haErrPropMemFail  OBJECT-TYPE
	SYNTAX  Counter64
	MAX-ACCESS  read-only
	STATUS  current
	DESCRIPTION
		"Total number of times memory allocation failed during command propagation."
	::= { nsHighAvailabilityGroup 9 }

haErrNsbMemFail  OBJECT-TYPE
	SYNTAX  Counter64
	MAX-ACCESS  read-only
	STATUS  current
	DESCRIPTION
		"Total number of times memory allocation failed while sending heartbeats."
	::= { nsHighAvailabilityGroup 10 }

haErrPortSilent  OBJECT-TYPE
	SYNTAX  Counter64
	MAX-ACCESS  read-only
	STATUS  current
	DESCRIPTION
		"Total number of times heartbeat packets were not received on any enabled interface for the duration of the Dead Interval."
	::= { nsHighAvailabilityGroup 11 }

haTotTimerRecoveries  OBJECT-TYPE
	SYNTAX  Counter64
	MAX-ACCESS  read-only
	STATUS  current
	DESCRIPTION
		"Total number of times HA engine recovered from tight loops (i.e., Total number of times HA timers are not called for max down time)."
	::= { nsHighAvailabilityGroup 12 }

haErrSwMonitorFail  OBJECT-TYPE
	SYNTAX  Counter64
	MAX-ACCESS  read-only
	STATUS  current
	DESCRIPTION
		"Total number of times heartbeats were not received from the peer node within the Hello Interval time."
	::= { nsHighAvailabilityGroup 13 }

haNicsMonitorFailed  OBJECT-TYPE
	SYNTAX  OCTET STRING
	MAX-ACCESS  read-only
	STATUS  current
	DESCRIPTION
		"Interfaces on which HA heartbeats are not being seen"
	::= { nsHighAvailabilityGroup 14 }

haLastMasterStateTransitionReason  OBJECT-TYPE
	SYNTAX  OCTET STRING
	MAX-ACCESS  read-only
	STATUS  current
	DESCRIPTION
		"The reason for the last master state transition. This gives the conditions under which this node assumed the current state. The current state         is available at the oid sysHighAvailabilityMode.0"
	::= { nsHighAvailabilityGroup 15 }

haPeerSystemState  OBJECT-TYPE
	SYNTAX  OCTET STRING
	MAX-ACCESS  accessible-for-notify
	STATUS  current
	DESCRIPTION
		"HA peer system state"
	::= { nsHighAvailabilityGroup 16 }

haErrPropTimeout  OBJECT-TYPE
	SYNTAX  Counter64
	MAX-ACCESS  read-only
	STATUS  current
	DESCRIPTION
		"Number of times propagation timed out"
	::= { nsHighAvailabilityGroup 17 }

haCurDerivedInc  OBJECT-TYPE
	SYNTAX  Counter32
	MAX-ACCESS  read-only
	STATUS  current
	DESCRIPTION
		"Derived incarnation based on ioctls received"
	::= { nsHighAvailabilityGroup 18 }

haCurPeerInc  OBJECT-TYPE
	SYNTAX  Counter32
	MAX-ACCESS  read-only
	STATUS  current
	DESCRIPTION
		"The peer's incarnation seen from heartbeats"
	::= { nsHighAvailabilityGroup 19 }

haErrMasterDispute  OBJECT-TYPE
	SYNTAX  Counter64
	MAX-ACCESS  read-only
	STATUS  current
	DESCRIPTION
		"Number of HA master dispute"
	::= { nsHighAvailabilityGroup 20 }

haTotPktTx  OBJECT-TYPE
	SYNTAX  Counter64
	MAX-ACCESS  read-only
	STATUS  current
	DESCRIPTION
		"Number of heartbeat packets sent to the peer node. Heartbeats are sent at regular intervals (default is 200 milliseconds) to determine the state of the peer node."
	::= { nsHighAvailabilityGroup 21 }

haTotPktRx  OBJECT-TYPE
	SYNTAX  Counter64
	MAX-ACCESS  read-only
	STATUS  current
	DESCRIPTION
		"Number of heartbeat packets received from the peer node. Heartbeats are sent at regular intervals (default is 200 milliseconds) to determine the state of the peer node."
	::= { nsHighAvailabilityGroup 22 }

haCurStatus  OBJECT-TYPE
	SYNTAX  HAON
	MAX-ACCESS  read-only
	STATUS  current
	DESCRIPTION
		"Indicates whether a NetScaler is set up for high availability. Possible values are YES and NO. If the value is NO, the high availability statistics below are invalid."
	::= { nsHighAvailabilityGroup 23 }

haCurState  OBJECT-TYPE
	SYNTAX  HAState
	MAX-ACCESS  read-only
	STATUS  current
	DESCRIPTION
		"State of the node, based on its health, in a high availability setup. Possible values are: 
UP – Indicates that the node is accessible and can function as either a primary or secondary node.
DISABLED – Indicates that the high availability status of the node has been manually disabled. Synchronization and propagation cannot take place between the peer nodes.
INIT – Indicates that the node is in the process of becoming part of the high availability configuration. 
PARTIALFAIL – Indicates that one of the high availability monitored interfaces has failed because of a card or link failure. This state triggers a failover.
COMPLETEFAIL – Indicates that all the interfaces of the node are unusable, because the interfaces on which high availability monitoring is enabled are not connected or are manually disabled. This state triggers a failover.
DUMB – Indicates that the node is in listening mode. It does not participate in high availability transitions or transfer configuration from the peer node. This is a configured value, not a statistic.
PARTIALFAILSSL – Indicates that the SSL card has failed. This state triggers a failover.
ROUTEMONITORFAIL – Indicates that the route monitor has failed. This state triggers a failover."
	::= { nsHighAvailabilityGroup 24 }

vlanTable  OBJECT-TYPE
	SYNTAX  SEQUENCE OF VlanEntry
	MAX-ACCESS  not-accessible
	STATUS  current
	DESCRIPTION
		"The vlan related statistics Table."
	::= { nsSysGroup 24 }

vlanEntry  OBJECT-TYPE
	SYNTAX  VlanEntry
	MAX-ACCESS  not-accessible
	STATUS  current
	DESCRIPTION
		"..."
	INDEX { vlanId   }
	::= { vlanTable 1 }

VlanEntry ::= SEQUENCE {
	vlanId  Integer32,
	vlanMemberInterfaces  OCTET STRING,
	vlanTaggedInterfaces  OCTET STRING,
	vlanTotRxPktsLow  Counter32,
	vlanTotRxPktsHigh  Counter32,
	vlanTotRxBytesLow  Counter32,
	vlanTotRxBytesHigh  Counter32,
	vlanTotTxPktsLow  Counter32,
	vlanTotTxPktsHigh  Counter32,
	vlanTotTxBytesLow  Counter32,
	vlanTotTxBytesHigh  Counter32,
	vlanTotDroppedPktsLow  Counter32,
	vlanTotDroppedPktsHigh  Counter32,
	vlanTotBroadcastPktsLow  Counter32,
	vlanTotBroadcastPktsHigh  Counter32,
	vlanTotRxPkts  Counter64,
	vlanTotRxBytes  Counter64,
	vlanTotTxPkts  Counter64,
	vlanTotTxBytes  Counter64,
	vlanTotDroppedPkts  Counter64,
	vlanTotBroadcastPkts  Counter64,
	vlanBindIpAddress  IpAddress,
	vlanBindIpNetmask  IpAddress
}

vlanId  OBJECT-TYPE
	SYNTAX  Integer32
	MAX-ACCESS  read-only
	STATUS  current
	DESCRIPTION
		"This represents the unique id of the vlan"
	::= { vlanEntry 1 }

vlanMemberInterfaces  OBJECT-TYPE
	SYNTAX  OCTET STRING
	MAX-ACCESS  read-only
	STATUS  current
	DESCRIPTION
		"This represents the list of interfaces on the NetScaler that are members of the vlan "
	::= { vlanEntry 2 }

vlanTaggedInterfaces  OBJECT-TYPE
	SYNTAX  OCTET STRING
	MAX-ACCESS  read-only
	STATUS  current
	DESCRIPTION
		"This represents the list of interfaces on the NetScaler that are members of the vlan that carry tagged packets"
	::= { vlanEntry 3 }

vlanTotRxPktsLow  OBJECT-TYPE
	SYNTAX  Counter32
	MAX-ACCESS  read-only
	STATUS  obsolete
	DESCRIPTION
		"...OBSOLETE"
	::= { vlanEntry 4 }

vlanTotRxPktsHigh  OBJECT-TYPE
	SYNTAX  Counter32
	MAX-ACCESS  read-only
	STATUS  obsolete
	DESCRIPTION
		"...OBSOLETE"
	::= { vlanEntry 5 }

vlanTotRxBytesLow  OBJECT-TYPE
	SYNTAX  Counter32
	MAX-ACCESS  read-only
	STATUS  obsolete
	DESCRIPTION
		"...OBSOLETE"
	::= { vlanEntry 6 }

vlanTotRxBytesHigh  OBJECT-TYPE
	SYNTAX  Counter32
	MAX-ACCESS  read-only
	STATUS  obsolete
	DESCRIPTION
		"...OBSOLETE"
	::= { vlanEntry 7 }

vlanTotTxPktsLow  OBJECT-TYPE
	SYNTAX  Counter32
	MAX-ACCESS  read-only
	STATUS  obsolete
	DESCRIPTION
		"...OBSOLETE"
	::= { vlanEntry 8 }

vlanTotTxPktsHigh  OBJECT-TYPE
	SYNTAX  Counter32
	MAX-ACCESS  read-only
	STATUS  obsolete
	DESCRIPTION
		"...OBSOLETE"
	::= { vlanEntry 9 }

vlanTotTxBytesLow  OBJECT-TYPE
	SYNTAX  Counter32
	MAX-ACCESS  read-only
	STATUS  obsolete
	DESCRIPTION
		"...OBSOLETE"
	::= { vlanEntry 10 }

vlanTotTxBytesHigh  OBJECT-TYPE
	SYNTAX  Counter32
	MAX-ACCESS  read-only
	STATUS  obsolete
	DESCRIPTION
		"...OBSOLETE"
	::= { vlanEntry 11 }

vlanTotDroppedPktsLow  OBJECT-TYPE
	SYNTAX  Counter32
	MAX-ACCESS  read-only
	STATUS  obsolete
	DESCRIPTION
		"...OBSOLETE"
	::= { vlanEntry 12 }

vlanTotDroppedPktsHigh  OBJECT-TYPE
	SYNTAX  Counter32
	MAX-ACCESS  read-only
	STATUS  obsolete
	DESCRIPTION
		"...OBSOLETE"
	::= { vlanEntry 13 }

vlanTotBroadcastPktsLow  OBJECT-TYPE
	SYNTAX  Counter32
	MAX-ACCESS  read-only
	STATUS  obsolete
	DESCRIPTION
		"...OBSOLETE"
	::= { vlanEntry 14 }

vlanTotBroadcastPktsHigh  OBJECT-TYPE
	SYNTAX  Counter32
	MAX-ACCESS  read-only
	STATUS  obsolete
	DESCRIPTION
		"...OBSOLETE"
	::= { vlanEntry 15 }

vlanTotRxPkts  OBJECT-TYPE
	SYNTAX  Counter64
	MAX-ACCESS  read-only
	STATUS  current
	DESCRIPTION
		"Packets received on the VLAN."
	::= { vlanEntry 16 }

vlanTotRxBytes  OBJECT-TYPE
	SYNTAX  Counter64
	MAX-ACCESS  read-only
	STATUS  current
	DESCRIPTION
		"Bytes of data received on the VLAN."
	::= { vlanEntry 17 }

vlanTotTxPkts  OBJECT-TYPE
	SYNTAX  Counter64
	MAX-ACCESS  read-only
	STATUS  current
	DESCRIPTION
		"Packets transmitted on the VLAN."
	::= { vlanEntry 18 }

vlanTotTxBytes  OBJECT-TYPE
	SYNTAX  Counter64
	MAX-ACCESS  read-only
	STATUS  current
	DESCRIPTION
		"Bytes of data transmitted on the VLAN."
	::= { vlanEntry 19 }

vlanTotDroppedPkts  OBJECT-TYPE
	SYNTAX  Counter64
	MAX-ACCESS  read-only
	STATUS  current
	DESCRIPTION
		"Inbound packets dropped by the VLAN upon reception."
	::= { vlanEntry 20 }

vlanTotBroadcastPkts  OBJECT-TYPE
	SYNTAX  Counter64
	MAX-ACCESS  read-only
	STATUS  current
	DESCRIPTION
		"Broadcast packets sent and received on the VLAN."
	::= { vlanEntry 21 }

vlanBindIpAddress  OBJECT-TYPE
	SYNTAX  IpAddress
	MAX-ACCESS  read-only
	STATUS  obsolete
	DESCRIPTION
		"...OBSOLETE"
	::= { vlanEntry 22 }

vlanBindIpNetmask  OBJECT-TYPE
	SYNTAX  IpAddress
	MAX-ACCESS  read-only
	STATUS  obsolete
	DESCRIPTION
		"...OBSOLETE"
	::= { vlanEntry 23 }

nsIpAddrTable  OBJECT-TYPE
	SYNTAX  SEQUENCE OF NsIpAddrEntry
	MAX-ACCESS  not-accessible
	STATUS  current
	DESCRIPTION
		"This table contains information about the IP addresses configured on the NetScaler."
	::= { nsSysGroup 26 }

nsIpAddrEntry  OBJECT-TYPE
	SYNTAX  NsIpAddrEntry
	MAX-ACCESS  not-accessible
	STATUS  current
	DESCRIPTION
		"..."
	INDEX { ipAddr   }
	::= { nsIpAddrTable 1 }

NsIpAddrEntry ::= SEQUENCE {
	ipAddr  IpAddress,
	ipNetmask  IpAddress,
	ipType  IpAddressType,
	ipMode  IpAddressMode,
	ipFreePorts  Gauge32,
	ipVlan  OCTET STRING
}

ipAddr  OBJECT-TYPE
	SYNTAX  IpAddress
	MAX-ACCESS  read-only
	STATUS  current
	DESCRIPTION
		"This represents an IP address configured on the NetScaler"
	::= { nsIpAddrEntry 1 }

ipNetmask  OBJECT-TYPE
	SYNTAX  IpAddress
	MAX-ACCESS  read-only
	STATUS  current
	DESCRIPTION
		"This represents the Netmask"
	::= { nsIpAddrEntry 2 }

ipType  OBJECT-TYPE
	SYNTAX  IpAddressType
	MAX-ACCESS  read-only
	STATUS  current
	DESCRIPTION
		"This represents the IP address type"
	::= { nsIpAddrEntry 3 }

ipMode  OBJECT-TYPE
	SYNTAX  IpAddressMode
	MAX-ACCESS  read-only
	STATUS  current
	DESCRIPTION
		"This represents the IP address mode"
	::= { nsIpAddrEntry 4 }

ipFreePorts  OBJECT-TYPE
	SYNTAX  Gauge32
	MAX-ACCESS  read-only
	STATUS  current
	DESCRIPTION
		"This represents the number of unused ports free on this IP"
	::= { nsIpAddrEntry 5 }

ipVlan  OBJECT-TYPE
	SYNTAX  OCTET STRING
	MAX-ACCESS  read-only
	STATUS  current
	DESCRIPTION
		"The vlan to which this ip address is bound."
	::= { nsIpAddrEntry 6 }

nsResourceGroup OBJECT IDENTIFIER
	::= { nsSysGroup 41 }

resCpuUsage  OBJECT-TYPE
	SYNTAX  Gauge32
	MAX-ACCESS  read-only
	STATUS  current
	DESCRIPTION
		"CPU utilization percentage"
	::= { nsResourceGroup 1 }

resMemUsage  OBJECT-TYPE
	SYNTAX  Gauge32
	MAX-ACCESS  read-only
	STATUS  current
	DESCRIPTION
		"This represents the percentage of memory utilization on NetScaler."
	::= { nsResourceGroup 2 }

numCPUs  OBJECT-TYPE
	SYNTAX  Integer32
	MAX-ACCESS  read-only
	STATUS  current
	DESCRIPTION
		"The number of CPUs on the system"
	::= { nsResourceGroup 3 }

memSizeMB  OBJECT-TYPE
	SYNTAX  Integer32
	MAX-ACCESS  read-only
	STATUS  current
	DESCRIPTION
		"Total amount of system memory, in megabytes"
	::= { nsResourceGroup 4 }

numSSLCards  OBJECT-TYPE
	SYNTAX  Integer32
	MAX-ACCESS  read-only
	STATUS  current
	DESCRIPTION
		"Number of SSL Cards on the system"
	::= { nsResourceGroup 5 }

nsCPUTable  OBJECT-TYPE
	SYNTAX  SEQUENCE OF NsCPUEntry
	MAX-ACCESS  not-accessible
	STATUS  current
	DESCRIPTION
		"This table contains information about each CPU in NetScaler."
	::= { nsResourceGroup 6 }

nsCPUEntry  OBJECT-TYPE
	SYNTAX  NsCPUEntry
	MAX-ACCESS  not-accessible
	STATUS  current
	DESCRIPTION
		"..."
	INDEX { nsCPUname   }
	::= { nsCPUTable 1 }

NsCPUEntry ::= SEQUENCE {
	nsCPUname  OCTET STRING,
	nsCPUusage  Gauge32
}

nsCPUname  OBJECT-TYPE
	SYNTAX  OCTET STRING
	MAX-ACCESS  read-only
	STATUS  current
	DESCRIPTION
		"The name of the CPU."
	::= { nsCPUEntry 1 }

nsCPUusage  OBJECT-TYPE
	SYNTAX  Gauge32
	MAX-ACCESS  read-only
	STATUS  current
	DESCRIPTION
		"CPU utilization percentage"
	::= { nsCPUEntry 2 }

nsSysHealthTable  OBJECT-TYPE
	SYNTAX  SEQUENCE OF NsSysHealthEntry
	MAX-ACCESS  not-accessible
	STATUS  current
	DESCRIPTION
		"This table contains information about the System Health status of the NetScaler."
	::= { nsResourceGroup 7 }

nsSysHealthEntry  OBJECT-TYPE
	SYNTAX  NsSysHealthEntry
	MAX-ACCESS  not-accessible
	STATUS  current
	DESCRIPTION
		"..."
	INDEX { sysHealthCounterName   }
	::= { nsSysHealthTable 1 }

NsSysHealthEntry ::= SEQUENCE {
	sysHealthCounterName  OCTET STRING,
	sysHealthCounterValue  Integer32
}

sysHealthCounterName  OBJECT-TYPE
	SYNTAX  OCTET STRING
	MAX-ACCESS  read-only
	STATUS  current
	DESCRIPTION
		"This is the health counter name. The counter name is composed with the type of the counter and what it is intended to carry. All voltage counters stats with 'v', fan counters starts with 'fan' and temperature counters starts with 't'. Eg:'v50p' is a voltage counter that carries the value of the +5v counter."
	::= { nsSysHealthEntry 1 }

sysHealthCounterValue  OBJECT-TYPE
	SYNTAX  Integer32
	MAX-ACCESS  read-only
	STATUS  current
	DESCRIPTION
		"The health counters value. The units are 'mv', RPM and degrees Celsius for voltage, fan and temperatures respectively."
	::= { nsSysHealthEntry 2 }

nsSysHealthDiskTable  OBJECT-TYPE
	SYNTAX  SEQUENCE OF NsSysHealthDiskEntry
	MAX-ACCESS  not-accessible
	STATUS  current
	DESCRIPTION
		"This table contains information about the disk space of the NetScaler."
	::= { nsResourceGroup 8 }

nsSysHealthDiskEntry  OBJECT-TYPE
	SYNTAX  NsSysHealthDiskEntry
	MAX-ACCESS  not-accessible
	STATUS  current
	DESCRIPTION
		"..."
	INDEX { sysHealthDiskName   }
	::= { nsSysHealthDiskTable 1 }

NsSysHealthDiskEntry ::= SEQUENCE {
	sysHealthDiskName  OCTET STRING,
	sysHealthDiskSize  Gauge32,
	sysHealthDiskAvail  Gauge32,
	sysHealthDiskUsed  Gauge32,
	sysHealthDiskPerusage  Gauge32
}

sysHealthDiskName  OBJECT-TYPE
	SYNTAX  OCTET STRING
	MAX-ACCESS  read-only
	STATUS  current
	DESCRIPTION
		"The disk name. Disk name always starts with the 'disk' keyword. Eg: disk0, disk1. Currently disk0 is mapped to /flash and disk1 mapped to /var partitions."
	::= { nsSysHealthDiskEntry 1 }

sysHealthDiskSize  OBJECT-TYPE
	SYNTAX  Gauge32
	MAX-ACCESS  read-only
	STATUS  current
	DESCRIPTION
		"The total disk space in MBytes (includes available and used spaces also)."
	::= { nsSysHealthDiskEntry 2 }

sysHealthDiskAvail  OBJECT-TYPE
	SYNTAX  Gauge32
	MAX-ACCESS  read-only
	STATUS  current
	DESCRIPTION
		"The total disk space available in MBytes."
	::= { nsSysHealthDiskEntry 3 }

sysHealthDiskUsed  OBJECT-TYPE
	SYNTAX  Gauge32
	MAX-ACCESS  read-only
	STATUS  current
	DESCRIPTION
		"The total disk space used in MBytes."
	::= { nsSysHealthDiskEntry 4 }

sysHealthDiskPerusage  OBJECT-TYPE
	SYNTAX  Gauge32
	MAX-ACCESS  read-only
	STATUS  current
	DESCRIPTION
		"The Percentage of the disk space used."
	::= { nsSysHealthDiskEntry 5 }

cpuSpeedMHz  OBJECT-TYPE
	SYNTAX  Integer32
	MAX-ACCESS  read-only
	STATUS  current
	DESCRIPTION
		"CPU speed in MHz"
	::= { nsResourceGroup 15 }

nsIpStatsGroup OBJECT IDENTIFIER
	::= { nsSysGroup 43 }

ipTotRxPktsLow  OBJECT-TYPE
	SYNTAX  Counter32
	MAX-ACCESS  read-only
	STATUS  obsolete
	DESCRIPTION
		"...OBSOLETE"
	::= { nsIpStatsGroup 1 }

ipTotRxPktsHigh  OBJECT-TYPE
	SYNTAX  Counter32
	MAX-ACCESS  read-only
	STATUS  obsolete
	DESCRIPTION
		"...OBSOLETE"
	::= { nsIpStatsGroup 2 }

ipTotRxBytesLow  OBJECT-TYPE
	SYNTAX  Counter32
	MAX-ACCESS  read-only
	STATUS  obsolete
	DESCRIPTION
		"...OBSOLETE"
	::= { nsIpStatsGroup 3 }

ipTotRxBytesHigh  OBJECT-TYPE
	SYNTAX  Counter32
	MAX-ACCESS  read-only
	STATUS  obsolete
	DESCRIPTION
		"...OBSOLETE"
	::= { nsIpStatsGroup 4 }

ipTotRxMbitsLow  OBJECT-TYPE
	SYNTAX  Counter32
	MAX-ACCESS  read-only
	STATUS  obsolete
	DESCRIPTION
		"...OBSOLETE"
	::= { nsIpStatsGroup 5 }

ipTotRxMbitsHigh  OBJECT-TYPE
	SYNTAX  Counter32
	MAX-ACCESS  read-only
	STATUS  obsolete
	DESCRIPTION
		"...OBSOLETE"
	::= { nsIpStatsGroup 6 }

ipTotTxPktsLow  OBJECT-TYPE
	SYNTAX  Counter32
	MAX-ACCESS  read-only
	STATUS  obsolete
	DESCRIPTION
		"...OBSOLETE"
	::= { nsIpStatsGroup 7 }

ipTotTxPktsHigh  OBJECT-TYPE
	SYNTAX  Counter32
	MAX-ACCESS  read-only
	STATUS  obsolete
	DESCRIPTION
		"...OBSOLETE"
	::= { nsIpStatsGroup 8 }

ipTotTxBytesLow  OBJECT-TYPE
	SYNTAX  Counter32
	MAX-ACCESS  read-only
	STATUS  obsolete
	DESCRIPTION
		"...OBSOLETE"
	::= { nsIpStatsGroup 9 }

ipTotTxBytesHigh  OBJECT-TYPE
	SYNTAX  Counter32
	MAX-ACCESS  read-only
	STATUS  obsolete
	DESCRIPTION
		"...OBSOLETE"
	::= { nsIpStatsGroup 10 }

ipTotTxMbitsLow  OBJECT-TYPE
	SYNTAX  Counter32
	MAX-ACCESS  read-only
	STATUS  obsolete
	DESCRIPTION
		"...OBSOLETE"
	::= { nsIpStatsGroup 11 }

ipTotTxMbitsHigh  OBJECT-TYPE
	SYNTAX  Counter32
	MAX-ACCESS  read-only
	STATUS  obsolete
	DESCRIPTION
		"...OBSOLETE"
	::= { nsIpStatsGroup 12 }

ipTotFragmentsLow  OBJECT-TYPE
	SYNTAX  Counter32
	MAX-ACCESS  read-only
	STATUS  obsolete
	DESCRIPTION
		"...OBSOLETE"
	::= { nsIpStatsGroup 13 }

ipTotFragmentsHigh  OBJECT-TYPE
	SYNTAX  Counter32
	MAX-ACCESS  read-only
	STATUS  obsolete
	DESCRIPTION
		"...OBSOLETE"
	::= { nsIpStatsGroup 14 }

ipTotBadlensLow  OBJECT-TYPE
	SYNTAX  Counter32
	MAX-ACCESS  read-only
	STATUS  obsolete
	DESCRIPTION
		"...OBSOLETE"
	::= { nsIpStatsGroup 15 }

ipTotBadlensHigh  OBJECT-TYPE
	SYNTAX  Counter32
	MAX-ACCESS  read-only
	STATUS  obsolete
	DESCRIPTION
		"...OBSOLETE"
	::= { nsIpStatsGroup 16 }

ipTotBadMacAddrsLow  OBJECT-TYPE
	SYNTAX  Counter32
	MAX-ACCESS  read-only
	STATUS  obsolete
	DESCRIPTION
		"...OBSOLETE"
	::= { nsIpStatsGroup 17 }

ipTotBadMacAddrsHigh  OBJECT-TYPE
	SYNTAX  Counter32
	MAX-ACCESS  read-only
	STATUS  obsolete
	DESCRIPTION
		"...OBSOLETE"
	::= { nsIpStatsGroup 18 }

ipTotMaxClientsLow  OBJECT-TYPE
	SYNTAX  Counter32
	MAX-ACCESS  read-only
	STATUS  obsolete
	DESCRIPTION
		"...OBSOLETE"
	::= { nsIpStatsGroup 19 }

ipTotMaxClientsHigh  OBJECT-TYPE
	SYNTAX  Counter32
	MAX-ACCESS  read-only
	STATUS  obsolete
	DESCRIPTION
		"...OBSOLETE"
	::= { nsIpStatsGroup 20 }

ipTotUnknownSvcsLow  OBJECT-TYPE
	SYNTAX  Counter32
	MAX-ACCESS  read-only
	STATUS  obsolete
	DESCRIPTION
		"...OBSOLETE"
	::= { nsIpStatsGroup 21 }

ipTotUnknownSvcsHigh  OBJECT-TYPE
	SYNTAX  Counter32
	MAX-ACCESS  read-only
	STATUS  obsolete
	DESCRIPTION
		"...OBSOLETE"
	::= { nsIpStatsGroup 22 }

ipTotLandattacksLow  OBJECT-TYPE
	SYNTAX  Counter32
	MAX-ACCESS  read-only
	STATUS  obsolete
	DESCRIPTION
		"...OBSOLETE"
	::= { nsIpStatsGroup 23 }

ipTotLandattacksHigh  OBJECT-TYPE
	SYNTAX  Counter32
	MAX-ACCESS  read-only
	STATUS  obsolete
	DESCRIPTION
		"...OBSOLETE"
	::= { nsIpStatsGroup 24 }

ipTotRxPkts  OBJECT-TYPE
	SYNTAX  Counter64
	MAX-ACCESS  read-only
	STATUS  current
	DESCRIPTION
		"IP packets received."
	::= { nsIpStatsGroup 25 }

ipTotRxBytes  OBJECT-TYPE
	SYNTAX  Counter64
	MAX-ACCESS  read-only
	STATUS  current
	DESCRIPTION
		"Bytes of IP data received."
	::= { nsIpStatsGroup 26 }

ipTotRxMbits  OBJECT-TYPE
	SYNTAX  Counter64
	MAX-ACCESS  read-only
	STATUS  current
	DESCRIPTION
		"Megabits of IP data received."
	::= { nsIpStatsGroup 27 }

ipTotTxPkts  OBJECT-TYPE
	SYNTAX  Counter64
	MAX-ACCESS  read-only
	STATUS  current
	DESCRIPTION
		"IP packets transmitted."
	::= { nsIpStatsGroup 28 }

ipTotTxBytes  OBJECT-TYPE
	SYNTAX  Counter64
	MAX-ACCESS  read-only
	STATUS  current
	DESCRIPTION
		"Bytes of IP data transmitted."
	::= { nsIpStatsGroup 29 }

ipTotTxMbits  OBJECT-TYPE
	SYNTAX  Counter64
	MAX-ACCESS  read-only
	STATUS  current
	DESCRIPTION
		"Megabits of IP data transmitted."
	::= { nsIpStatsGroup 30 }

ipTotFragments  OBJECT-TYPE
	SYNTAX  Counter64
	MAX-ACCESS  read-only
	STATUS  current
	DESCRIPTION
		"IP fragments received."
	::= { nsIpStatsGroup 31 }

ipTotBadlens  OBJECT-TYPE
	SYNTAX  Counter64
	MAX-ACCESS  read-only
	STATUS  current
	DESCRIPTION
		"Packets received with a length greater than the normal maximum transmission unit of 1514 bytes."
	::= { nsIpStatsGroup 32 }

ipTotBadMacAddrs  OBJECT-TYPE
	SYNTAX  Counter64
	MAX-ACCESS  read-only
	STATUS  current
	DESCRIPTION
		"IP packets transmitted with a bad MAC address."
	::= { nsIpStatsGroup 33 }

ipTotMaxClients  OBJECT-TYPE
	SYNTAX  Counter64
	MAX-ACCESS  read-only
	STATUS  current
	DESCRIPTION
		"Attempts to open a new connection to a service for which the maximum limit has been exceeded. Default value, 0, applies no limit."
	::= { nsIpStatsGroup 34 }

ipTotUnknownSvcs  OBJECT-TYPE
	SYNTAX  Counter64
	MAX-ACCESS  read-only
	STATUS  current
	DESCRIPTION
		"Packets received on a port or service that is not configured."
	::= { nsIpStatsGroup 35 }

ipTotLandattacks  OBJECT-TYPE
	SYNTAX  Counter64
	MAX-ACCESS  read-only
	STATUS  current
	DESCRIPTION
		"Land-attack packets received. The source and destination addresses are the same."
	::= { nsIpStatsGroup 36 }

ipTotBadChecksums  OBJECT-TYPE
	SYNTAX  Counter64
	MAX-ACCESS  read-only
	STATUS  current
	DESCRIPTION
		"Packets received with an IP checksum error."
	::= { nsIpStatsGroup 37 }

ipTotReassemblyAttempt  OBJECT-TYPE
	SYNTAX  Counter64
	MAX-ACCESS  read-only
	STATUS  current
	DESCRIPTION
		"IP packets that the NetScaler attempts to reassemble. If one of the fragments is missing, the whole packet is dropped."
	::= { nsIpStatsGroup 38 }

ipTotSuccReassembly  OBJECT-TYPE
	SYNTAX  Counter64
	MAX-ACCESS  read-only
	STATUS  current
	DESCRIPTION
		"Fragmented IP packets successfully reassembled on the NetScaler."
	::= { nsIpStatsGroup 39 }

ipTotUnsuccReassembly  OBJECT-TYPE
	SYNTAX  Counter64
	MAX-ACCESS  read-only
	STATUS  current
	DESCRIPTION
		"Packets received that could not be reassembled. This can occur when there is a checksum failure, an identification field mismatch, or when one of the fragments is missing."
	::= { nsIpStatsGroup 40 }

ipTotTooBig  OBJECT-TYPE
	SYNTAX  Counter64
	MAX-ACCESS  read-only
	STATUS  current
	DESCRIPTION
		"Packets received for which the reassembled data exceeds the Ethernet packet data length of 1500 bytes."
	::= { nsIpStatsGroup 41 }

ipTotZeroFragmentLen  OBJECT-TYPE
	SYNTAX  Counter64
	MAX-ACCESS  read-only
	STATUS  current
	DESCRIPTION
		"Packets received with a fragment length of 0 bytes."
	::= { nsIpStatsGroup 42 }

ipTotDupFragments  OBJECT-TYPE
	SYNTAX  Counter64
	MAX-ACCESS  read-only
	STATUS  current
	DESCRIPTION
		"Duplicate IP fragments received. This can occur when the acknowledgement was not received within the expected time."
	::= { nsIpStatsGroup 43 }

ipTotOutOfOrderFrag  OBJECT-TYPE
	SYNTAX  Counter64
	MAX-ACCESS  read-only
	STATUS  current
	DESCRIPTION
		"Fragments received that are out of order."
	::= { nsIpStatsGroup 44 }

ipTotUnknownDstRcvd  OBJECT-TYPE
	SYNTAX  Counter64
	MAX-ACCESS  read-only
	STATUS  current
	DESCRIPTION
		"Packets received in which the destination IP address was not reachable or not owned by the NetScaler."
	::= { nsIpStatsGroup 45 }

ipTotBadTransport  OBJECT-TYPE
	SYNTAX  Counter64
	MAX-ACCESS  read-only
	STATUS  current
	DESCRIPTION
		"Packets received in which the protocol specified in the IP header is unknown to the NetScaler."
	::= { nsIpStatsGroup 46 }

ipTotVIPDown  OBJECT-TYPE
	SYNTAX  Counter64
	MAX-ACCESS  read-only
	STATUS  current
	DESCRIPTION
		"Packets received for which the VIP is down. This can occur when all the services bound to the VIP are down or the VIP is manually disabled."
	::= { nsIpStatsGroup 47 }

ipTotFixHeaderFail  OBJECT-TYPE
	SYNTAX  Counter64
	MAX-ACCESS  read-only
	STATUS  current
	DESCRIPTION
		"Packets received that contain an error in one or more components of the IP header."
	::= { nsIpStatsGroup 48 }

ipTotAddrLookup  OBJECT-TYPE
	SYNTAX  Counter64
	MAX-ACCESS  read-only
	STATUS  current
	DESCRIPTION
		"IP address lookups performed by the NetScaler. When a packet is received on a non-established session, the NetScaler checks if the destination IP address is one of the NetScaler owned IP addresses."
	::= { nsIpStatsGroup 49 }

ipTotAddrLookupFail  OBJECT-TYPE
	SYNTAX  Counter64
	MAX-ACCESS  read-only
	STATUS  current
	DESCRIPTION
		"IP address lookups performed by the NetScaler that have failed because the destination IP address of the packet does not match any of the NetScaler owned IP addresses."
	::= { nsIpStatsGroup 50 }

ipTotUDPfragmentsFwd  OBJECT-TYPE
	SYNTAX  Counter64
	MAX-ACCESS  read-only
	STATUS  current
	DESCRIPTION
		"UDP fragments forwarded to the client or the server."
	::= { nsIpStatsGroup 51 }

ipTotTCPfragmentsFwd  OBJECT-TYPE
	SYNTAX  Counter64
	MAX-ACCESS  read-only
	STATUS  current
	DESCRIPTION
		"TCP fragments forwarded to the client or the server."
	::= { nsIpStatsGroup 52 }

ipTotFragPktsGen  OBJECT-TYPE
	SYNTAX  Counter64
	MAX-ACCESS  read-only
	STATUS  current
	DESCRIPTION
		"Fragmented packets created by the NetScaler."
	::= { nsIpStatsGroup 53 }

ipTotInvalidHeaderSz  OBJECT-TYPE
	SYNTAX  Counter64
	MAX-ACCESS  read-only
	STATUS  current
	DESCRIPTION
		"Packets received in which an invalid data length is specified, or the value in the length field and the actual data length do not match. The range for the Ethernet packet data length is 0-1500 bytes."
	::= { nsIpStatsGroup 54 }

ipTotInvalidPacketSize  OBJECT-TYPE
	SYNTAX  Counter64
	MAX-ACCESS  read-only
	STATUS  current
	DESCRIPTION
		"Total number of packets received by NetScaler with invalid IP packet size."
	::= { nsIpStatsGroup 55 }

ipTotTruncatedPackets  OBJECT-TYPE
	SYNTAX  Counter64
	MAX-ACCESS  read-only
	STATUS  current
	DESCRIPTION
		"Truncated IP packets received. An overflow in the routers along the path can truncate IP packets."
	::= { nsIpStatsGroup 56 }

ipTotZeroNextHop  OBJECT-TYPE
	SYNTAX  Counter64
	MAX-ACCESS  read-only
	STATUS  current
	DESCRIPTION
		"Packets received that contain a 0 value in the next hop field. These packets are dropped."
	::= { nsIpStatsGroup 57 }

ipTotTtlExpired  OBJECT-TYPE
	SYNTAX  Counter64
	MAX-ACCESS  read-only
	STATUS  current
	DESCRIPTION
		"Packets for which the time-to-live (TTL) expired during transit. These packets are dropped."
	::= { nsIpStatsGroup 58 }

nonIpTotTruncatedPackets  OBJECT-TYPE
	SYNTAX  Counter64
	MAX-ACCESS  read-only
	STATUS  current
	DESCRIPTION
		"Truncated non-IP packets received."
	::= { nsIpStatsGroup 59 }

nsIcmpStatsGroup OBJECT IDENTIFIER
	::= { nsSysGroup 44 }

icmpTotRxPktsLow  OBJECT-TYPE
	SYNTAX  Counter32
	MAX-ACCESS  read-only
	STATUS  obsolete
	DESCRIPTION
		"...OBSOLETE"
	::= { nsIcmpStatsGroup 1 }

icmpTotRxPktsHigh  OBJECT-TYPE
	SYNTAX  Counter32
	MAX-ACCESS  read-only
	STATUS  obsolete
	DESCRIPTION
		"...OBSOLETE"
	::= { nsIcmpStatsGroup 2 }

icmpTotRxBytesLow  OBJECT-TYPE
	SYNTAX  Counter32
	MAX-ACCESS  read-only
	STATUS  obsolete
	DESCRIPTION
		"...OBSOLETE"
	::= { nsIcmpStatsGroup 3 }

icmpTotRxBytesHigh  OBJECT-TYPE
	SYNTAX  Counter32
	MAX-ACCESS  read-only
	STATUS  obsolete
	DESCRIPTION
		"...OBSOLETE"
	::= { nsIcmpStatsGroup 4 }

icmpTotTxPktsLow  OBJECT-TYPE
	SYNTAX  Counter32
	MAX-ACCESS  read-only
	STATUS  obsolete
	DESCRIPTION
		"...OBSOLETE"
	::= { nsIcmpStatsGroup 5 }

icmpTotTxPktsHigh  OBJECT-TYPE
	SYNTAX  Counter32
	MAX-ACCESS  read-only
	STATUS  obsolete
	DESCRIPTION
		"...OBSOLETE"
	::= { nsIcmpStatsGroup 6 }

icmpTotTxBytesLow  OBJECT-TYPE
	SYNTAX  Counter32
	MAX-ACCESS  read-only
	STATUS  obsolete
	DESCRIPTION
		"...OBSOLETE"
	::= { nsIcmpStatsGroup 7 }

icmpTotTxBytesHigh  OBJECT-TYPE
	SYNTAX  Counter32
	MAX-ACCESS  read-only
	STATUS  obsolete
	DESCRIPTION
		"...OBSOLETE"
	::= { nsIcmpStatsGroup 8 }

icmpTotRxEchoReplyLow  OBJECT-TYPE
	SYNTAX  Counter32
	MAX-ACCESS  read-only
	STATUS  obsolete
	DESCRIPTION
		"...OBSOLETE"
	::= { nsIcmpStatsGroup 9 }

icmpTotRxEchoReplyHigh  OBJECT-TYPE
	SYNTAX  Counter32
	MAX-ACCESS  read-only
	STATUS  obsolete
	DESCRIPTION
		"...OBSOLETE"
	::= { nsIcmpStatsGroup 10 }

icmpTotTxEchoReplyLow  OBJECT-TYPE
	SYNTAX  Counter32
	MAX-ACCESS  read-only
	STATUS  obsolete
	DESCRIPTION
		"...OBSOLETE"
	::= { nsIcmpStatsGroup 11 }

icmpTotTxEchoReplyHigh  OBJECT-TYPE
	SYNTAX  Counter32
	MAX-ACCESS  read-only
	STATUS  obsolete
	DESCRIPTION
		"...OBSOLETE"
	::= { nsIcmpStatsGroup 12 }

icmpTotRxEchoLow  OBJECT-TYPE
	SYNTAX  Counter32
	MAX-ACCESS  read-only
	STATUS  obsolete
	DESCRIPTION
		"...OBSOLETE"
	::= { nsIcmpStatsGroup 13 }

icmpTotRxEchoHigh  OBJECT-TYPE
	SYNTAX  Counter32
	MAX-ACCESS  read-only
	STATUS  obsolete
	DESCRIPTION
		"...OBSOLETE"
	::= { nsIcmpStatsGroup 14 }

icmpTotPktsDroppedLow  OBJECT-TYPE
	SYNTAX  Counter32
	MAX-ACCESS  read-only
	STATUS  obsolete
	DESCRIPTION
		"...OBSOLETE"
	::= { nsIcmpStatsGroup 15 }

icmpTotPktsDroppedHigh  OBJECT-TYPE
	SYNTAX  Counter32
	MAX-ACCESS  read-only
	STATUS  obsolete
	DESCRIPTION
		"...OBSOLETE"
	::= { nsIcmpStatsGroup 16 }

icmpCurRateThreshold  OBJECT-TYPE
	SYNTAX  Integer32
	MAX-ACCESS  read-only
	STATUS  current
	DESCRIPTION
		"Limit for ICMP packets handled every 10 milliseconds. Default value, 0, applies no limit.
This is a configurable value using the set rateControl command.
 "
	::= { nsIcmpStatsGroup 17 }

icmpCurRateThresholdInterval  OBJECT-TYPE
	SYNTAX  Integer32
	MAX-ACCESS  read-only
	STATUS  obsolete
	DESCRIPTION
		"...OBSOLETE"
	::= { nsIcmpStatsGroup 18 }

icmpCurRateCounter  OBJECT-TYPE
	SYNTAX  Counter32
	MAX-ACCESS  read-only
	STATUS  obsolete
	DESCRIPTION
		"...OBSOLETE"
	::= { nsIcmpStatsGroup 19 }

icmpTotThresholdExceedsLow  OBJECT-TYPE
	SYNTAX  Counter32
	MAX-ACCESS  read-only
	STATUS  obsolete
	DESCRIPTION
		"...OBSOLETE"
	::= { nsIcmpStatsGroup 20 }

icmpTotThresholdExceedsHigh  OBJECT-TYPE
	SYNTAX  Counter32
	MAX-ACCESS  read-only
	STATUS  obsolete
	DESCRIPTION
		"...OBSOLETE"
	::= { nsIcmpStatsGroup 21 }

icmpTotRxPkts  OBJECT-TYPE
	SYNTAX  Counter64
	MAX-ACCESS  read-only
	STATUS  current
	DESCRIPTION
		"ICMP packets received."
	::= { nsIcmpStatsGroup 22 }

icmpTotRxBytes  OBJECT-TYPE
	SYNTAX  Counter64
	MAX-ACCESS  read-only
	STATUS  current
	DESCRIPTION
		"Bytes of ICMP data received."
	::= { nsIcmpStatsGroup 23 }

icmpTotTxPkts  OBJECT-TYPE
	SYNTAX  Counter64
	MAX-ACCESS  read-only
	STATUS  current
	DESCRIPTION
		"ICMP packets transmitted."
	::= { nsIcmpStatsGroup 24 }

icmpTotTxBytes  OBJECT-TYPE
	SYNTAX  Counter64
	MAX-ACCESS  read-only
	STATUS  current
	DESCRIPTION
		"Bytes of ICMP data transmitted."
	::= { nsIcmpStatsGroup 25 }

icmpTotRxEchoReply  OBJECT-TYPE
	SYNTAX  Counter64
	MAX-ACCESS  read-only
	STATUS  current
	DESCRIPTION
		"ICMP Ping echo replies received."
	::= { nsIcmpStatsGroup 26 }

icmpTotTxEchoReply  OBJECT-TYPE
	SYNTAX  Counter64
	MAX-ACCESS  read-only
	STATUS  current
	DESCRIPTION
		"ICMP Ping echo replies transmitted."
	::= { nsIcmpStatsGroup 27 }

icmpTotRxEcho  OBJECT-TYPE
	SYNTAX  Counter64
	MAX-ACCESS  read-only
	STATUS  current
	DESCRIPTION
		"ICMP Ping Echo Request and Echo Reply packets received."
	::= { nsIcmpStatsGroup 28 }

icmpTotPktsDropped  OBJECT-TYPE
	SYNTAX  Counter64
	MAX-ACCESS  read-only
	STATUS  current
	DESCRIPTION
		"ICMP packets dropped because the rate threshold has been exceeded."
	::= { nsIcmpStatsGroup 29 }

icmpTotThresholdExceeds  OBJECT-TYPE
	SYNTAX  Counter64
	MAX-ACCESS  read-only
	STATUS  current
	DESCRIPTION
		"Times the ICMP rate threshold is exceeded. If this counter continuously increases, first make sure the ICMP packets received are genuine. If they are, increase the current rate threshold."
	::= { nsIcmpStatsGroup 30 }

icmpTotPortUnreachableRx  OBJECT-TYPE
	SYNTAX  Counter64
	MAX-ACCESS  read-only
	STATUS  current
	DESCRIPTION
		"ICMP Port Unreachable error messages received. This error is generated when there is no service is running on the port."
	::= { nsIcmpStatsGroup 31 }

icmpTotPortUnreachableTx  OBJECT-TYPE
	SYNTAX  Counter64
	MAX-ACCESS  read-only
	STATUS  current
	DESCRIPTION
		"ICMP Port Unreachable error messages generated. This error is generated when there is no service is running on the port."
	::= { nsIcmpStatsGroup 32 }

icmpTotBadChecksum  OBJECT-TYPE
	SYNTAX  Counter64
	MAX-ACCESS  read-only
	STATUS  current
	DESCRIPTION
		"ICMP Fragmentation Needed error messages received with an ICMP checksum error."
	::= { nsIcmpStatsGroup 33 }

icmpTotNeedFragRx  OBJECT-TYPE
	SYNTAX  Counter64
	MAX-ACCESS  read-only
	STATUS  current
	DESCRIPTION
		"ICMP Fragmentation Needed error messages received for packets that need to be fragmented but for which Don't Fragment is specified the header."
	::= { nsIcmpStatsGroup 34 }

icmpTotNonFirstIpFrag  OBJECT-TYPE
	SYNTAX  Counter64
	MAX-ACCESS  read-only
	STATUS  current
	DESCRIPTION
		"ICMP Fragmentation Needed error messages received that were generated by an IP fragment other than the first one."
	::= { nsIcmpStatsGroup 35 }

icmpTotInvalidBodyLen  OBJECT-TYPE
	SYNTAX  Counter64
	MAX-ACCESS  read-only
	STATUS  current
	DESCRIPTION
		"ICMP Fragmentation Needed error messages received that specified an invalid body length."
	::= { nsIcmpStatsGroup 36 }

icmpTotNoTcpConn  OBJECT-TYPE
	SYNTAX  Counter64
	MAX-ACCESS  read-only
	STATUS  current
	DESCRIPTION
		"ICMP Need Fragmentation error messages received for TCP packets. The state of the connection for these packets is not maintained on the NetScaler."
	::= { nsIcmpStatsGroup 37 }

icmpTotNoUdpConn  OBJECT-TYPE
	SYNTAX  Counter64
	MAX-ACCESS  read-only
	STATUS  current
	DESCRIPTION
		"ICMP Need Fragmentation error messages received for UDP packets. The state of the connection for these packets is not maintained on the NetScaler."
	::= { nsIcmpStatsGroup 38 }

icmpTotInvalidTcpSeqno  OBJECT-TYPE
	SYNTAX  Counter64
	MAX-ACCESS  read-only
	STATUS  current
	DESCRIPTION
		"ICMP Fragmentation Needed error messages received for packets that contain an invalid TCP address."
	::= { nsIcmpStatsGroup 39 }

icmpTotInvalidNextMTUval  OBJECT-TYPE
	SYNTAX  Counter64
	MAX-ACCESS  read-only
	STATUS  current
	DESCRIPTION
		"ICMP Fragmentation Needed error messages received in which the Maximum Transmission Unit (MTU) for the next hop is out of range. The range for the MTU is 576-1500."
	::= { nsIcmpStatsGroup 40 }

icmpTotDstIpLookup  OBJECT-TYPE
	SYNTAX  Counter64
	MAX-ACCESS  read-only
	STATUS  current
	DESCRIPTION
		"Total number of MTU lookup on destination IP info received on a need fragmentation ICMP error message failed."
	::= { nsIcmpStatsGroup 41 }

icmpTotBigNextMTU  OBJECT-TYPE
	SYNTAX  Counter64
	MAX-ACCESS  read-only
	STATUS  current
	DESCRIPTION
		"ICMP Fragmentation Needed error messages received in which the value for the next MTU is higher than that of the current MTU."
	::= { nsIcmpStatsGroup 42 }

icmpTotInvalidProtocol  OBJECT-TYPE
	SYNTAX  Counter64
	MAX-ACCESS  read-only
	STATUS  current
	DESCRIPTION
		"ICMP Fragmentation Needed error messages received that contain a protocol other than TCP and UDP."
	::= { nsIcmpStatsGroup 43 }

icmpTotBadPMTUIpChecksum  OBJECT-TYPE
	SYNTAX  Counter64
	MAX-ACCESS  read-only
	STATUS  current
	DESCRIPTION
		"ICMP Fragmentation Needed error messages received with an IP checksum error."
	::= { nsIcmpStatsGroup 44 }

icmpTotPMTUnoLink  OBJECT-TYPE
	SYNTAX  Counter64
	MAX-ACCESS  read-only
	STATUS  current
	DESCRIPTION
		"ICMP Fragmentation Needed error messages received on a Protocol Control Block (PCB) with no link. The PCB maintains the state of the connection."
	::= { nsIcmpStatsGroup 45 }

icmpTotPMTUDiscoveryDisabled  OBJECT-TYPE
	SYNTAX  Counter64
	MAX-ACCESS  read-only
	STATUS  current
	DESCRIPTION
		"ICMP Need Fragmentation error messages received when the PMTU Discovery mode is not enabled."
	::= { nsIcmpStatsGroup 46 }

nsUdpStatsGroup OBJECT IDENTIFIER
	::= { nsSysGroup 45 }

udpTotUnknownSvcPktsLow  OBJECT-TYPE
	SYNTAX  Counter32
	MAX-ACCESS  read-only
	STATUS  obsolete
	DESCRIPTION
		"...OBSOLETE"
	::= { nsUdpStatsGroup 1 }

udpTotUnknownSvcPktsHigh  OBJECT-TYPE
	SYNTAX  Counter32
	MAX-ACCESS  read-only
	STATUS  obsolete
	DESCRIPTION
		"...OBSOLETE"
	::= { nsUdpStatsGroup 2 }

udpTotRxPktsLow  OBJECT-TYPE
	SYNTAX  Counter32
	MAX-ACCESS  read-only
	STATUS  obsolete
	DESCRIPTION
		"...OBSOLETE"
	::= { nsUdpStatsGroup 3 }

udpTotRxPktsHigh  OBJECT-TYPE
	SYNTAX  Counter32
	MAX-ACCESS  read-only
	STATUS  obsolete
	DESCRIPTION
		"...OBSOLETE"
	::= { nsUdpStatsGroup 4 }

udpTotRxBytesLow  OBJECT-TYPE
	SYNTAX  Counter32
	MAX-ACCESS  read-only
	STATUS  obsolete
	DESCRIPTION
		"...OBSOLETE"
	::= { nsUdpStatsGroup 5 }

udpTotRxBytesHigh  OBJECT-TYPE
	SYNTAX  Counter32
	MAX-ACCESS  read-only
	STATUS  obsolete
	DESCRIPTION
		"...OBSOLETE"
	::= { nsUdpStatsGroup 6 }

udpTotTxPktsLow  OBJECT-TYPE
	SYNTAX  Counter32
	MAX-ACCESS  read-only
	STATUS  obsolete
	DESCRIPTION
		"...OBSOLETE"
	::= { nsUdpStatsGroup 7 }

udpTotTxPktsHigh  OBJECT-TYPE
	SYNTAX  Counter32
	MAX-ACCESS  read-only
	STATUS  obsolete
	DESCRIPTION
		"...OBSOLETE"
	::= { nsUdpStatsGroup 8 }

udpTotTxBytesLow  OBJECT-TYPE
	SYNTAX  Counter32
	MAX-ACCESS  read-only
	STATUS  obsolete
	DESCRIPTION
		"...OBSOLETE"
	::= { nsUdpStatsGroup 9 }

udpTotTxBytesHigh  OBJECT-TYPE
	SYNTAX  Counter32
	MAX-ACCESS  read-only
	STATUS  obsolete
	DESCRIPTION
		"...OBSOLETE"
	::= { nsUdpStatsGroup 10 }

udpCurRateThreshold  OBJECT-TYPE
	SYNTAX  Counter32
	MAX-ACCESS  read-only
	STATUS  current
	DESCRIPTION
		"Limit for UDP packets handled every 10 milliseconds. Default value, 0, applies no limit.
This is a configurable value using the set rateControl command.
 "
	::= { nsUdpStatsGroup 11 }

udpRateInterval  OBJECT-TYPE
	SYNTAX  Counter32
	MAX-ACCESS  read-only
	STATUS  obsolete
	DESCRIPTION
		"...OBSOLETE"
	::= { nsUdpStatsGroup 12 }

udpCurRateCounter  OBJECT-TYPE
	SYNTAX  Counter32
	MAX-ACCESS  read-only
	STATUS  obsolete
	DESCRIPTION
		"...OBSOLETE"
	::= { nsUdpStatsGroup 13 }

udpCurRateThresholdExceedsLow  OBJECT-TYPE
	SYNTAX  Counter32
	MAX-ACCESS  read-only
	STATUS  obsolete
	DESCRIPTION
		"...OBSOLETE"
	::= { nsUdpStatsGroup 14 }

udpCurRateThresholdExceedsHigh  OBJECT-TYPE
	SYNTAX  Counter32
	MAX-ACCESS  read-only
	STATUS  obsolete
	DESCRIPTION
		"...OBSOLETE"
	::= { nsUdpStatsGroup 15 }

udpTotUnknownSvcPkts  OBJECT-TYPE
	SYNTAX  Counter64
	MAX-ACCESS  read-only
	STATUS  current
	DESCRIPTION
		"UDP packets received (but dropped) on a NetScaler port number that is not assigned to any service."
	::= { nsUdpStatsGroup 16 }

udpTotRxPkts  OBJECT-TYPE
	SYNTAX  Counter64
	MAX-ACCESS  read-only
	STATUS  current
	DESCRIPTION
		"UDP packets received."
	::= { nsUdpStatsGroup 17 }

udpTotRxBytes  OBJECT-TYPE
	SYNTAX  Counter64
	MAX-ACCESS  read-only
	STATUS  current
	DESCRIPTION
		"Bytes of UDP data received."
	::= { nsUdpStatsGroup 18 }

udpTotTxPkts  OBJECT-TYPE
	SYNTAX  Counter64
	MAX-ACCESS  read-only
	STATUS  current
	DESCRIPTION
		"UDP packets transmitted."
	::= { nsUdpStatsGroup 19 }

udpTotTxBytes  OBJECT-TYPE
	SYNTAX  Counter64
	MAX-ACCESS  read-only
	STATUS  current
	DESCRIPTION
		"Bytes of UDP data transmitted."
	::= { nsUdpStatsGroup 20 }

udpCurRateThresholdExceeds  OBJECT-TYPE
	SYNTAX  Counter64
	MAX-ACCESS  read-only
	STATUS  current
	DESCRIPTION
		"Number of times the UDP rate threshold is exceeded. If this counter continuously increases, first make sure the UDP packets received are genuine. If they are, increase the current rate threshold.
	"
	::= { nsUdpStatsGroup 21 }

udpBadChecksum  OBJECT-TYPE
	SYNTAX  Counter64
	MAX-ACCESS  read-only
	STATUS  current
	DESCRIPTION
		"Packets received with a UDP checksum error."
	::= { nsUdpStatsGroup 22 }

nsTcpStatsGroup OBJECT IDENTIFIER
	::= { nsSysGroup 46 }

tcpCurServerConn  OBJECT-TYPE
	SYNTAX  Gauge32
	MAX-ACCESS  read-only
	STATUS  current
	DESCRIPTION
		"Server connections, including connections in the Opening, Established, and Closing state."
	::= { nsTcpStatsGroup 1 }

tcpCurClientConn  OBJECT-TYPE
	SYNTAX  Gauge32
	MAX-ACCESS  read-only
	STATUS  current
	DESCRIPTION
		"Client connections, including connections in the Opening, Established, and Closing state."
	::= { nsTcpStatsGroup 2 }

tcpCurPendingConn  OBJECT-TYPE
	SYNTAX  Gauge32
	MAX-ACCESS  read-only
	STATUS  obsolete
	DESCRIPTION
		"...OBSOLETE"
	::= { nsTcpStatsGroup 3 }

tcpCurResetCount  OBJECT-TYPE
	SYNTAX  Counter32
	MAX-ACCESS  read-only
	STATUS  obsolete
	DESCRIPTION
		"...OBSOLETE"
	::= { nsTcpStatsGroup 4 }

tcpMaxServerConnections  OBJECT-TYPE
	SYNTAX  Integer32
	MAX-ACCESS  read-only
	STATUS  obsolete
	DESCRIPTION
		"...OBSOLETE"
	::= { nsTcpStatsGroup 5 }

tcpMaxReqsperConn  OBJECT-TYPE
	SYNTAX  Integer32
	MAX-ACCESS  read-only
	STATUS  obsolete
	DESCRIPTION
		"...OBSOLETE"
	::= { nsTcpStatsGroup 6 }

tcpMaxPerSrvrReusePool  OBJECT-TYPE
	SYNTAX  Integer32
	MAX-ACCESS  read-only
	STATUS  obsolete
	DESCRIPTION
		"...OBSOLETE"
	::= { nsTcpStatsGroup 7 }

tcpActiveServerConn  OBJECT-TYPE
	SYNTAX  Gauge32
	MAX-ACCESS  read-only
	STATUS  current
	DESCRIPTION
		"Connections to a server currently responding to requests."
	::= { nsTcpStatsGroup 8 }

tcpCurClientConnClosing  OBJECT-TYPE
	SYNTAX  Gauge32
	MAX-ACCESS  read-only
	STATUS  current
	DESCRIPTION
		"Client connections in the Closing state, which indicates that the connection termination process has initiated but is not complete."
	::= { nsTcpStatsGroup 9 }

tcpCurServerConnEstablished  OBJECT-TYPE
	SYNTAX  Gauge32
	MAX-ACCESS  read-only
	STATUS  current
	DESCRIPTION
		"Current server connections in the Established state, which indicates that data transfer can occur between the NetScaler and the server."
	::= { nsTcpStatsGroup 10 }

tcpCurClientConnOpening  OBJECT-TYPE
	SYNTAX  Gauge32
	MAX-ACCESS  read-only
	STATUS  current
	DESCRIPTION
		"Client connections in the Opening state, which indicates that the handshakes are not yet complete."
	::= { nsTcpStatsGroup 11 }

tcpCurClientConnEstablished  OBJECT-TYPE
	SYNTAX  Gauge32
	MAX-ACCESS  read-only
	STATUS  current
	DESCRIPTION
		"Current client connections in the Established state, which indicates that data transfer can occur between the NetScaler and the client."
	::= { nsTcpStatsGroup 12 }

tcpCurServerConnClosing  OBJECT-TYPE
	SYNTAX  Gauge32
	MAX-ACCESS  read-only
	STATUS  current
	DESCRIPTION
		"Server connections in the Closing state, which indicates that the connection termination process has initiated but is not complete."
	::= { nsTcpStatsGroup 13 }

tcpSpareConn  OBJECT-TYPE
	SYNTAX  Gauge32
	MAX-ACCESS  read-only
	STATUS  current
	DESCRIPTION
		"Spare connections available. To save time and resources in establishing another connection for a new client, the connection on the server is not closed after completing the request from the first client and is available for serving future requests."
	::= { nsTcpStatsGroup 14 }

tcpSurgeQueueLen  OBJECT-TYPE
	SYNTAX  Gauge32
	MAX-ACCESS  read-only
	STATUS  current
	DESCRIPTION
		"Connections in the surge queue. When the NetScaler cannot open a connection to the server, for example when maximum connections have been reached, the NetScaler queues these requests."
	::= { nsTcpStatsGroup 15 }

tcpCurServerConnOpening  OBJECT-TYPE
	SYNTAX  Gauge32
	MAX-ACCESS  read-only
	STATUS  current
	DESCRIPTION
		"Server connections in the Opening state, which indicates that the handshakes are not yet complete."
	::= { nsTcpStatsGroup 16 }

tcpTotServerConnOpened  OBJECT-TYPE
	SYNTAX  Counter64
	MAX-ACCESS  read-only
	STATUS  current
	DESCRIPTION
		"Server connections initiated by the NetScaler since startup. This counter is reset when the NetScaler is restarted."
	::= { nsTcpStatsGroup 17 }

tcpTotServerConnClosed  OBJECT-TYPE
	SYNTAX  Counter64
	MAX-ACCESS  read-only
	STATUS  current
	DESCRIPTION
		"Total number of closed server connections"
	::= { nsTcpStatsGroup 18 }

tcpTotClientConnOpened  OBJECT-TYPE
	SYNTAX  Counter64
	MAX-ACCESS  read-only
	STATUS  current
	DESCRIPTION
		"Client connections initiated on the NetScaler since startup. This counter is reset when the NetScaler is restarted."
	::= { nsTcpStatsGroup 19 }

tcpTotClientConnClosed  OBJECT-TYPE
	SYNTAX  Counter64
	MAX-ACCESS  read-only
	STATUS  current
	DESCRIPTION
		"Total number of closed client connections"
	::= { nsTcpStatsGroup 20 }

tcpTotSyn  OBJECT-TYPE
	SYNTAX  Counter64
	MAX-ACCESS  read-only
	STATUS  current
	DESCRIPTION
		"SYN packets received"
	::= { nsTcpStatsGroup 21 }

tcpTotSynProbe  OBJECT-TYPE
	SYNTAX  Counter64
	MAX-ACCESS  read-only
	STATUS  current
	DESCRIPTION
		"Probes from the NetScaler to a server. The NetScaler sends a SYN packet to the server to check its availability and expects a SYN_ACK packet from the server before a specified response timeout."
	::= { nsTcpStatsGroup 22 }

tcpTotSvrFin  OBJECT-TYPE
	SYNTAX  Counter64
	MAX-ACCESS  read-only
	STATUS  current
	DESCRIPTION
		"FIN packets received from the server."
	::= { nsTcpStatsGroup 23 }

tcpTotCltFin  OBJECT-TYPE
	SYNTAX  Counter64
	MAX-ACCESS  read-only
	STATUS  current
	DESCRIPTION
		"FIN packets received from the clients."
	::= { nsTcpStatsGroup 24 }

tcpWaitToSyn  OBJECT-TYPE
	SYNTAX  Counter64
	MAX-ACCESS  read-only
	STATUS  current
	DESCRIPTION
		"SYN packets received on connections that are in the TIME_WAIT state. Packets cannot be transferred on a connection in this state."
	::= { nsTcpStatsGroup 25 }

tcpTotZombieCltConnFlushed  OBJECT-TYPE
	SYNTAX  Counter64
	MAX-ACCESS  read-only
	STATUS  current
	DESCRIPTION
		"Client connections that are flushed because the client has been idle for some time."
	::= { nsTcpStatsGroup 26 }

tcpTotZombieSvrConnFlushed  OBJECT-TYPE
	SYNTAX  Counter64
	MAX-ACCESS  read-only
	STATUS  current
	DESCRIPTION
		"Server connections that are flushed because there have been no client requests in the queue for some time."
	::= { nsTcpStatsGroup 27 }

tcpTotZombieHalfOpenCltConnFlushed  OBJECT-TYPE
	SYNTAX  Counter64
	MAX-ACCESS  read-only
	STATUS  current
	DESCRIPTION
		"Half-opened client connections that are flushed because the three-way handshakes are not complete."
	::= { nsTcpStatsGroup 28 }

tcpTotZombieHalfOpenSvrConnFlushed  OBJECT-TYPE
	SYNTAX  Counter64
	MAX-ACCESS  read-only
	STATUS  current
	DESCRIPTION
		"Half-opened server connections that are flushed because the three-way handshakes are not complete."
	::= { nsTcpStatsGroup 29 }

tcpTotZombieActiveHalfCloseCltConnFlushed  OBJECT-TYPE
	SYNTAX  Counter64
	MAX-ACCESS  read-only
	STATUS  current
	DESCRIPTION
		"Active half-closed client connections that are flushed because the client has closed the connection and there has been no activity on the connection."
	::= { nsTcpStatsGroup 30 }

tcpTotZombieActiveHalfCloseSvrConnFlushed  OBJECT-TYPE
	SYNTAX  Counter64
	MAX-ACCESS  read-only
	STATUS  current
	DESCRIPTION
		"Active half-closed server connections that are flushed because the server has closed the connection and there has been no activity on the connection."
	::= { nsTcpStatsGroup 31 }

tcpTotZombiePassiveHalfCloseCltConnFlushed  OBJECT-TYPE
	SYNTAX  Counter64
	MAX-ACCESS  read-only
	STATUS  current
	DESCRIPTION
		"Passive half-closed client connections that are flushed because the NetScaler has closed the connection and there has been no activity on the connection."
	::= { nsTcpStatsGroup 32 }

tcpTotZombiePassiveHalfCloseSrvConnFlushed  OBJECT-TYPE
	SYNTAX  Counter64
	MAX-ACCESS  read-only
	STATUS  current
	DESCRIPTION
		"Passive half-closed server connections that are flushed because the NetScaler has closed the connection and there has been no activity on the connection."
	::= { nsTcpStatsGroup 33 }

tcpErrBadCheckSum  OBJECT-TYPE
	SYNTAX  Counter64
	MAX-ACCESS  read-only
	STATUS  current
	DESCRIPTION
		"Packets received with a TCP checksum error."
	::= { nsTcpStatsGroup 34 }

tcpErrSynInSynRcvd  OBJECT-TYPE
	SYNTAX  Counter64
	MAX-ACCESS  read-only
	STATUS  current
	DESCRIPTION
		"SYN packets received on a connection that is in the SYN_RCVD state. A connection goes into the SYN_RCVD state after receiving a SYN packet."
	::= { nsTcpStatsGroup 35 }

tcpErrSynInEst  OBJECT-TYPE
	SYNTAX  Counter64
	MAX-ACCESS  read-only
	STATUS  current
	DESCRIPTION
		"SYN packets received on a connection that is in the ESTABLISHED state. A SYN packet is not expected on an ESTABLISHED connection."
	::= { nsTcpStatsGroup 36 }

tcpErrSynGiveUp  OBJECT-TYPE
	SYNTAX  Counter64
	MAX-ACCESS  read-only
	STATUS  current
	DESCRIPTION
		"Attempts to establish a connection on the NetScaler that timed out."
	::= { nsTcpStatsGroup 37 }

tcpErrSynSentBadAck  OBJECT-TYPE
	SYNTAX  Counter64
	MAX-ACCESS  read-only
	STATUS  current
	DESCRIPTION
		"Incorrect ACK packets received on a connection that is in the SYN_SENT state. An incorrect ACK packet is the third packet in the three-way handshake that has an incorrect sequence number."
	::= { nsTcpStatsGroup 38 }

tcpErrSynRetry  OBJECT-TYPE
	SYNTAX  Counter64
	MAX-ACCESS  read-only
	STATUS  current
	DESCRIPTION
		"SYN packets resent to a server."
	::= { nsTcpStatsGroup 39 }

tcpErrFinRetry  OBJECT-TYPE
	SYNTAX  Counter64
	MAX-ACCESS  read-only
	STATUS  current
	DESCRIPTION
		"FIN packets resent to a server or a client."
	::= { nsTcpStatsGroup 40 }

tcpErrFinGiveUp  OBJECT-TYPE
	SYNTAX  Counter64
	MAX-ACCESS  read-only
	STATUS  current
	DESCRIPTION
		"Connections that were timed out by the NetScaler because of not receiving the ACK packet after retransmitting the FIN packet four times."
	::= { nsTcpStatsGroup 41 }

tcpErrFinDup  OBJECT-TYPE
	SYNTAX  Counter64
	MAX-ACCESS  read-only
	STATUS  current
	DESCRIPTION
		"Number of duplicate FIN packets was recieved"
	::= { nsTcpStatsGroup 42 }

tcpErrRst  OBJECT-TYPE
	SYNTAX  Counter64
	MAX-ACCESS  read-only
	STATUS  current
	DESCRIPTION
		"Reset packets received from a client or a server."
	::= { nsTcpStatsGroup 43 }

tcpErrRstNonEst  OBJECT-TYPE
	SYNTAX  Counter64
	MAX-ACCESS  read-only
	STATUS  current
	DESCRIPTION
		"Reset packets received on a connection that is not in the ESTABLISHED state."
	::= { nsTcpStatsGroup 44 }

tcpErrRstOutOfWindow  OBJECT-TYPE
	SYNTAX  Counter64
	MAX-ACCESS  read-only
	STATUS  current
	DESCRIPTION
		"Reset packets received on a connection that is out of the current TCP window."
	::= { nsTcpStatsGroup 45 }

tcpErrRstInTimewait  OBJECT-TYPE
	SYNTAX  Counter64
	MAX-ACCESS  read-only
	STATUS  current
	DESCRIPTION
		"Reset packets received on a connection that is in the TIME_WAIT state. Packets cannot be transferred on a connection in the TIME_WAIT state."
	::= { nsTcpStatsGroup 46 }

tcpErrSvrRetrasmit  OBJECT-TYPE
	SYNTAX  Counter64
	MAX-ACCESS  read-only
	STATUS  current
	DESCRIPTION
		"Packets retransmitted by a server. This usually occurs because the acknowledgement from the NetScaler has not reached the server."
	::= { nsTcpStatsGroup 47 }

tcpErrCltRetrasmit  OBJECT-TYPE
	SYNTAX  Counter64
	MAX-ACCESS  read-only
	STATUS  current
	DESCRIPTION
		"Packets retransmitted by a client. This usually occurs because the acknowledgement from the NetScaler has not reached the client."
	::= { nsTcpStatsGroup 48 }

tcpErrFullRetrasmit  OBJECT-TYPE
	SYNTAX  Counter64
	MAX-ACCESS  read-only
	STATUS  current
	DESCRIPTION
		"Full packets retransmitted by the client or the server."
	::= { nsTcpStatsGroup 49 }

tcpErrPartialRetrasmit  OBJECT-TYPE
	SYNTAX  Counter64
	MAX-ACCESS  read-only
	STATUS  current
	DESCRIPTION
		"Partial packet retransmits by a client or server due to congestion on the connection. This usually occurs because the window advertised by the NetScaler is not big enough to hold the full packet."
	::= { nsTcpStatsGroup 50 }

tcpErrSvrOutOfOrder  OBJECT-TYPE
	SYNTAX  Counter64
	MAX-ACCESS  read-only
	STATUS  current
	DESCRIPTION
		"Out of order TCP packets received from a server. "
	::= { nsTcpStatsGroup 51 }

tcpErrCltOutOfOrder  OBJECT-TYPE
	SYNTAX  Counter64
	MAX-ACCESS  read-only
	STATUS  current
	DESCRIPTION
		"Out of order TCP packets received from a client."
	::= { nsTcpStatsGroup 52 }

tcpErrCltHole  OBJECT-TYPE
	SYNTAX  Counter64
	MAX-ACCESS  read-only
	STATUS  current
	DESCRIPTION
		"TCP holes created on a client connection. When out of order packets are received from a client, a hole is created on the NetScaler for each group of missing packets."
	::= { nsTcpStatsGroup 53 }

tcpErrSvrHole  OBJECT-TYPE
	SYNTAX  Counter64
	MAX-ACCESS  read-only
	STATUS  current
	DESCRIPTION
		"TCP holes created on a server connection. When out of order packets are received from a server, a hole is created on the NetScaler for each group of missing packets."
	::= { nsTcpStatsGroup 54 }

tcpErrCookiePktSeqReject  OBJECT-TYPE
	SYNTAX  Counter64
	MAX-ACCESS  read-only
	STATUS  current
	DESCRIPTION
		"SYN cookie packets rejected because they contain an incorrect sequence number."
	::= { nsTcpStatsGroup 55 }

tcpErrCookiePktSigReject  OBJECT-TYPE
	SYNTAX  Counter64
	MAX-ACCESS  read-only
	STATUS  current
	DESCRIPTION
		"SYN cookie packets rejected because they contain an incorrect signature."
	::= { nsTcpStatsGroup 56 }

tcpErrCookiePktSeqDrop  OBJECT-TYPE
	SYNTAX  Counter64
	MAX-ACCESS  read-only
	STATUS  current
	DESCRIPTION
		"SYN cookie packets dropped because the sequence number specified in the packets is outside the current window."
	::= { nsTcpStatsGroup 57 }

tcpErrCookiePktMssReject  OBJECT-TYPE
	SYNTAX  Counter64
	MAX-ACCESS  read-only
	STATUS  current
	DESCRIPTION
		"SYN cookie packets rejected because the maximum segment size (MSS) specified in the packets is incorrect."
	::= { nsTcpStatsGroup 58 }

tcpErrRetransmit  OBJECT-TYPE
	SYNTAX  Counter64
	MAX-ACCESS  read-only
	STATUS  current
	DESCRIPTION
		"TCP packets retransmitted. The NetScaler attempts to retransmit the packet up to seven times, after which it resets the other half of the TCP connection."
	::= { nsTcpStatsGroup 59 }

tcpErrRetransmitGiveUp  OBJECT-TYPE
	SYNTAX  Counter64
	MAX-ACCESS  read-only
	STATUS  current
	DESCRIPTION
		"Times the NetScaler terminates a connection after retransmitting the packet seven times on that connection."
	::= { nsTcpStatsGroup 60 }

tcpTotRxPkts  OBJECT-TYPE
	SYNTAX  Counter64
	MAX-ACCESS  read-only
	STATUS  current
	DESCRIPTION
		"TCP packets received."
	::= { nsTcpStatsGroup 61 }

tcpTotRxBytes  OBJECT-TYPE
	SYNTAX  Counter64
	MAX-ACCESS  read-only
	STATUS  current
	DESCRIPTION
		"Bytes of TCP data received."
	::= { nsTcpStatsGroup 62 }

tcpTotTxPkts  OBJECT-TYPE
	SYNTAX  Counter64
	MAX-ACCESS  read-only
	STATUS  current
	DESCRIPTION
		"TCP packets transmitted."
	::= { nsTcpStatsGroup 63 }

tcpTotTxBytes  OBJECT-TYPE
	SYNTAX  Counter64
	MAX-ACCESS  read-only
	STATUS  current
	DESCRIPTION
		"Bytes of TCP data transmitted."
	::= { nsTcpStatsGroup 64 }

pcbTotZombieCall  OBJECT-TYPE
	SYNTAX  Counter64
	MAX-ACCESS  read-only
	STATUS  current
	DESCRIPTION
		"Times the Zombie cleanup function is called. Every time a connection is flushed, it is marked for cleanup. The Zombie cleanup function clears all these connections at predefined intervals."
	::= { nsTcpStatsGroup 65 }

tcpTotSynHeld  OBJECT-TYPE
	SYNTAX  Counter64
	MAX-ACCESS  read-only
	STATUS  current
	DESCRIPTION
		"SYN packets held on the NetScaler that are waiting for a server connection."
	::= { nsTcpStatsGroup 66 }

tcpTotSynFlush  OBJECT-TYPE
	SYNTAX  Counter64
	MAX-ACCESS  read-only
	STATUS  current
	DESCRIPTION
		"SYN packets flushed on the NetScaler because of no response from the server for three or more seconds."
	::= { nsTcpStatsGroup 67 }

tcpTotFinWaitClosed  OBJECT-TYPE
	SYNTAX  Counter64
	MAX-ACCESS  read-only
	STATUS  current
	DESCRIPTION
		"Connections closed on the NetScaler because the number of connections in the TIME_WAIT state has exceeded the default value of 7000."
	::= { nsTcpStatsGroup 68 }

tcpErrAnyPortFail  OBJECT-TYPE
	SYNTAX  Counter64
	MAX-ACCESS  read-only
	STATUS  current
	DESCRIPTION
		"Port allocations that have failed on a mapped IP address because the maximum limit of 65536 has been exceeded, or the mapped IP is not configured."
	::= { nsTcpStatsGroup 69 }

tcpErrIpPortFail  OBJECT-TYPE
	SYNTAX  Counter64
	MAX-ACCESS  read-only
	STATUS  current
	DESCRIPTION
		"Port allocations that have failed on a subnet IP address or vserver IP address because the maximum limit of 65536 has been exceeded."
	::= { nsTcpStatsGroup 70 }

tcpErrSentRst  OBJECT-TYPE
	SYNTAX  Counter64
	MAX-ACCESS  read-only
	STATUS  current
	DESCRIPTION
		"Reset packets sent to a client or a server."
	::= { nsTcpStatsGroup 71 }

tcpErrBadStateConn  OBJECT-TYPE
	SYNTAX  Counter64
	MAX-ACCESS  read-only
	STATUS  current
	DESCRIPTION
		"Connections that are not in a valid TCP state."
	::= { nsTcpStatsGroup 72 }

tcpErrFastRetransmissions  OBJECT-TYPE
	SYNTAX  Counter64
	MAX-ACCESS  read-only
	STATUS  current
	DESCRIPTION
		"TCP packets on which the NetScaler performs a fast retransmission in response to three duplicate acknowledgements or a partial acknowledgement.  The NetScaler assumes that the packet is lost and retransmits the packet before its time-out."
	::= { nsTcpStatsGroup 73 }

tcpErrFirstRetransmissions  OBJECT-TYPE
	SYNTAX  Counter64
	MAX-ACCESS  read-only
	STATUS  current
	DESCRIPTION
		"Packets retransmitted once by the NetScaler."
	::= { nsTcpStatsGroup 74 }

tcpErrSecondRetransmissions  OBJECT-TYPE
	SYNTAX  Counter64
	MAX-ACCESS  read-only
	STATUS  current
	DESCRIPTION
		"Packets retransmitted twice by the NetScaler."
	::= { nsTcpStatsGroup 75 }

tcpErrThirdRetransmissions  OBJECT-TYPE
	SYNTAX  Counter64
	MAX-ACCESS  read-only
	STATUS  current
	DESCRIPTION
		"Packets retransmitted three times by the NetScaler."
	::= { nsTcpStatsGroup 76 }

tcpErrForthRetransmissions  OBJECT-TYPE
	SYNTAX  Counter64
	MAX-ACCESS  read-only
	STATUS  current
	DESCRIPTION
		"Packets retransmitted four times by the NetScaler."
	::= { nsTcpStatsGroup 77 }

tcpErrFifthRetransmissions  OBJECT-TYPE
	SYNTAX  Counter64
	MAX-ACCESS  read-only
	STATUS  current
	DESCRIPTION
		"Packets retransmitted five times by the NetScaler."
	::= { nsTcpStatsGroup 78 }

tcpErrSixthRetransmissions  OBJECT-TYPE
	SYNTAX  Counter64
	MAX-ACCESS  read-only
	STATUS  current
	DESCRIPTION
		"Packets retransmitted six times by the NetScaler."
	::= { nsTcpStatsGroup 79 }

tcpErrSeventhRetransmissions  OBJECT-TYPE
	SYNTAX  Counter64
	MAX-ACCESS  read-only
	STATUS  current
	DESCRIPTION
		"Packets retransmitted seven times by the NetScaler. If this fails, the NetScaler terminates the connection."
	::= { nsTcpStatsGroup 80 }

tcpErrDataAfterFin  OBJECT-TYPE
	SYNTAX  Counter64
	MAX-ACCESS  read-only
	STATUS  current
	DESCRIPTION
		"Bytes received following a connection termination request. This error is usually caused by a reordering of packets during transmission."
	::= { nsTcpStatsGroup 81 }

tcpErrRstThreshold  OBJECT-TYPE
	SYNTAX  Counter64
	MAX-ACCESS  read-only
	STATUS  current
	DESCRIPTION
		"Reset packets dropped because the default threshold of 100 resets per 10 milliseconds has been exceeded. This is a configurable value using the set rateControl command."
	::= { nsTcpStatsGroup 82 }

tcpErrOutOfWindowPkts  OBJECT-TYPE
	SYNTAX  Counter64
	MAX-ACCESS  read-only
	STATUS  current
	DESCRIPTION
		"Packets received that are out of the current advertised window."
	::= { nsTcpStatsGroup 83 }

tcpErrSynDroppedCongestion  OBJECT-TYPE
	SYNTAX  Counter64
	MAX-ACCESS  read-only
	STATUS  current
	DESCRIPTION
		"SYN packets dropped because of network congestion."
	::= { nsTcpStatsGroup 84 }

tcpCurPhysicalServers  OBJECT-TYPE
	SYNTAX  Gauge32
	MAX-ACCESS  read-only
	STATUS  current
	DESCRIPTION
		"The number of physical servers that Netscaler has open connections with."
	::= { nsTcpStatsGroup 85 }

tcpReuseHit  OBJECT-TYPE
	SYNTAX  Gauge32
	MAX-ACCESS  read-only
	STATUS  current
	DESCRIPTION
		"Total no of client transactions found the server connection in the reuse-pool."
	::= { nsTcpStatsGroup 86 }

tcpWaitToData  OBJECT-TYPE
	SYNTAX  Counter64
	MAX-ACCESS  read-only
	STATUS  current
	DESCRIPTION
		"Bytes of data received on connections that are in the TIME_WAIT state. Data cannot be transferred on a connection that is in this state."
	::= { nsTcpStatsGroup 87 }

tcpErrStrayPkt  OBJECT-TYPE
	SYNTAX  Counter64
	MAX-ACCESS  read-only
	STATUS  current
	DESCRIPTION
		"Packets received on a connection whose state is not maintained on the NetScaler."
	::= { nsTcpStatsGroup 88 }

tcpTotClientConnOpenRate  OBJECT-TYPE
	SYNTAX  OCTET STRING
	MAX-ACCESS  read-only
	STATUS  current
	DESCRIPTION
		"Rate at which connections are opened in the system."
	::= { nsTcpStatsGroup 89 }

nsSslStatsGroup OBJECT IDENTIFIER
	::= { nsSysGroup 47 }

sslCardStatus  OBJECT-TYPE
	SYNTAX  Integer32
	MAX-ACCESS  read-only
	STATUS  current
	DESCRIPTION
		"Status of the  SSL card (1=UP, 0=DOWN)"
	::= { nsSslStatsGroup 1 }

sslEngineStatus  OBJECT-TYPE
	SYNTAX  Integer32
	MAX-ACCESS  read-only
	STATUS  current
	DESCRIPTION
		"Status of the SSL Engine (1=UP/0=DOWN). This state is decided based on SSL Feature/License status and minimum number of cards UP"
	::= { nsSslStatsGroup 2 }

sslSessionsPerSec  OBJECT-TYPE
	SYNTAX  Gauge32
	MAX-ACCESS  read-only
	STATUS  current
	DESCRIPTION
		"SSL sessions/second between client and NetScaler."
	::= { nsSslStatsGroup 3 }

sslTotTransactionsLow  OBJECT-TYPE
	SYNTAX  Counter32
	MAX-ACCESS  read-only
	STATUS  obsolete
	DESCRIPTION
		"...OBSOLETE"
	::= { nsSslStatsGroup 11 }

sslTotTransactionsHigh  OBJECT-TYPE
	SYNTAX  Counter32
	MAX-ACCESS  read-only
	STATUS  obsolete
	DESCRIPTION
		"...OBSOLETE"
	::= { nsSslStatsGroup 12 }

sslTotSSLv2TransactionsLow  OBJECT-TYPE
	SYNTAX  Counter32
	MAX-ACCESS  read-only
	STATUS  obsolete
	DESCRIPTION
		"...OBSOLETE"
	::= { nsSslStatsGroup 13 }

sslTotSSLv2TransactionsHigh  OBJECT-TYPE
	SYNTAX  Counter32
	MAX-ACCESS  read-only
	STATUS  obsolete
	DESCRIPTION
		"...OBSOLETE"
	::= { nsSslStatsGroup 14 }

sslTotSSLv3TransactionsLow  OBJECT-TYPE
	SYNTAX  Counter32
	MAX-ACCESS  read-only
	STATUS  obsolete
	DESCRIPTION
		"...OBSOLETE"
	::= { nsSslStatsGroup 15 }

sslTotSSLv3TransactionsHigh  OBJECT-TYPE
	SYNTAX  Counter32
	MAX-ACCESS  read-only
	STATUS  obsolete
	DESCRIPTION
		"...OBSOLETE"
	::= { nsSslStatsGroup 16 }

sslTotTLSv1TransactionsLow  OBJECT-TYPE
	SYNTAX  Counter32
	MAX-ACCESS  read-only
	STATUS  obsolete
	DESCRIPTION
		"...OBSOLETE"
	::= { nsSslStatsGroup 17 }

sslTotTLSv1TransactionsHigh  OBJECT-TYPE
	SYNTAX  Counter32
	MAX-ACCESS  read-only
	STATUS  obsolete
	DESCRIPTION
		"...OBSOLETE"
	::= { nsSslStatsGroup 18 }

sslTotSessionsLow  OBJECT-TYPE
	SYNTAX  Counter32
	MAX-ACCESS  read-only
	STATUS  obsolete
	DESCRIPTION
		"...OBSOLETE"
	::= { nsSslStatsGroup 19 }

sslTotSessionsHigh  OBJECT-TYPE
	SYNTAX  Counter32
	MAX-ACCESS  read-only
	STATUS  obsolete
	DESCRIPTION
		"...OBSOLETE"
	::= { nsSslStatsGroup 20 }

sslTotSSLv2SessionsLow  OBJECT-TYPE
	SYNTAX  Counter32
	MAX-ACCESS  read-only
	STATUS  obsolete
	DESCRIPTION
		"...OBSOLETE"
	::= { nsSslStatsGroup 21 }

sslTotSSLv2SessionsHigh  OBJECT-TYPE
	SYNTAX  Counter32
	MAX-ACCESS  read-only
	STATUS  obsolete
	DESCRIPTION
		"...OBSOLETE"
	::= { nsSslStatsGroup 22 }

sslTotSSLv3SessionsLow  OBJECT-TYPE
	SYNTAX  Counter32
	MAX-ACCESS  read-only
	STATUS  obsolete
	DESCRIPTION
		"...OBSOLETE"
	::= { nsSslStatsGroup 23 }

sslTotSSLv3SessionsHigh  OBJECT-TYPE
	SYNTAX  Counter32
	MAX-ACCESS  read-only
	STATUS  obsolete
	DESCRIPTION
		"...OBSOLETE"
	::= { nsSslStatsGroup 24 }

sslTotTLSv1SessionsLow  OBJECT-TYPE
	SYNTAX  Counter32
	MAX-ACCESS  read-only
	STATUS  obsolete
	DESCRIPTION
		"...OBSOLETE"
	::= { nsSslStatsGroup 25 }

sslTotTLSv1SessionsHigh  OBJECT-TYPE
	SYNTAX  Counter32
	MAX-ACCESS  read-only
	STATUS  obsolete
	DESCRIPTION
		"...OBSOLETE"
	::= { nsSslStatsGroup 26 }

sslTotExpiredSessionsLow  OBJECT-TYPE
	SYNTAX  Counter32
	MAX-ACCESS  read-only
	STATUS  obsolete
	DESCRIPTION
		"...OBSOLETE"
	::= { nsSslStatsGroup 27 }

sslTotExpiredSessionsHigh  OBJECT-TYPE
	SYNTAX  Counter32
	MAX-ACCESS  read-only
	STATUS  obsolete
	DESCRIPTION
		"...OBSOLETE"
	::= { nsSslStatsGroup 28 }

sslTotNewSessionsLow  OBJECT-TYPE
	SYNTAX  Counter32
	MAX-ACCESS  read-only
	STATUS  obsolete
	DESCRIPTION
		"...OBSOLETE"
	::= { nsSslStatsGroup 29 }

sslTotNewSessionsHigh  OBJECT-TYPE
	SYNTAX  Counter32
	MAX-ACCESS  read-only
	STATUS  obsolete
	DESCRIPTION
		"...OBSOLETE"
	::= { nsSslStatsGroup 30 }

sslTotSessionHitsLow  OBJECT-TYPE
	SYNTAX  Counter32
	MAX-ACCESS  read-only
	STATUS  obsolete
	DESCRIPTION
		"...OBSOLETE"
	::= { nsSslStatsGroup 31 }

sslTotSessionHitsHigh  OBJECT-TYPE
	SYNTAX  Counter32
	MAX-ACCESS  read-only
	STATUS  obsolete
	DESCRIPTION
		"...OBSOLETE"
	::= { nsSslStatsGroup 32 }

sslTotSessionMissLow  OBJECT-TYPE
	SYNTAX  Counter32
	MAX-ACCESS  read-only
	STATUS  obsolete
	DESCRIPTION
		"...OBSOLETE"
	::= { nsSslStatsGroup 33 }

sslTotSessionMissHigh  OBJECT-TYPE
	SYNTAX  Counter32
	MAX-ACCESS  read-only
	STATUS  obsolete
	DESCRIPTION
		"...OBSOLETE"
	::= { nsSslStatsGroup 34 }

sslTotRenegSessionsLow  OBJECT-TYPE
	SYNTAX  Counter32
	MAX-ACCESS  read-only
	STATUS  obsolete
	DESCRIPTION
		"...OBSOLETE"
	::= { nsSslStatsGroup 35 }

sslTotRenegSessionsHigh  OBJECT-TYPE
	SYNTAX  Counter32
	MAX-ACCESS  read-only
	STATUS  obsolete
	DESCRIPTION
		"...OBSOLETE"
	::= { nsSslStatsGroup 36 }

sslTotSSLv3RenegSessionsLow  OBJECT-TYPE
	SYNTAX  Counter32
	MAX-ACCESS  read-only
	STATUS  obsolete
	DESCRIPTION
		"...OBSOLETE"
	::= { nsSslStatsGroup 37 }

sslTotSSLv3RenegSessionsHigh  OBJECT-TYPE
	SYNTAX  Counter32
	MAX-ACCESS  read-only
	STATUS  obsolete
	DESCRIPTION
		"...OBSOLETE"
	::= { nsSslStatsGroup 38 }

sslTotTLSv1RenegSessionsLow  OBJECT-TYPE
	SYNTAX  Counter32
	MAX-ACCESS  read-only
	STATUS  obsolete
	DESCRIPTION
		"...OBSOLETE"
	::= { nsSslStatsGroup 39 }

sslTotTLSv1RenegSessionsHigh  OBJECT-TYPE
	SYNTAX  Counter32
	MAX-ACCESS  read-only
	STATUS  obsolete
	DESCRIPTION
		"...OBSOLETE"
	::= { nsSslStatsGroup 40 }

sslTotSSLv2HandshakesLow  OBJECT-TYPE
	SYNTAX  Counter32
	MAX-ACCESS  read-only
	STATUS  obsolete
	DESCRIPTION
		"...OBSOLETE"
	::= { nsSslStatsGroup 41 }

sslTotSSLv2HandshakesHigh  OBJECT-TYPE
	SYNTAX  Counter32
	MAX-ACCESS  read-only
	STATUS  obsolete
	DESCRIPTION
		"...OBSOLETE"
	::= { nsSslStatsGroup 42 }

sslTotSSLv3HandshakesLow  OBJECT-TYPE
	SYNTAX  Counter32
	MAX-ACCESS  read-only
	STATUS  obsolete
	DESCRIPTION
		"...OBSOLETE"
	::= { nsSslStatsGroup 43 }

sslTotSSLv3HandshakesHigh  OBJECT-TYPE
	SYNTAX  Counter32
	MAX-ACCESS  read-only
	STATUS  obsolete
	DESCRIPTION
		"...OBSOLETE"
	::= { nsSslStatsGroup 44 }

sslTotTLSv1HandshakesLow  OBJECT-TYPE
	SYNTAX  Counter32
	MAX-ACCESS  read-only
	STATUS  obsolete
	DESCRIPTION
		"...OBSOLETE"
	::= { nsSslStatsGroup 45 }

sslTotTLSv1HandshakesHigh  OBJECT-TYPE
	SYNTAX  Counter32
	MAX-ACCESS  read-only
	STATUS  obsolete
	DESCRIPTION
		"...OBSOLETE"
	::= { nsSslStatsGroup 46 }

sslTotSSLv2ClientAuthenticationsLow  OBJECT-TYPE
	SYNTAX  Counter32
	MAX-ACCESS  read-only
	STATUS  obsolete
	DESCRIPTION
		"...OBSOLETE"
	::= { nsSslStatsGroup 47 }

sslTotSSLv2ClientAuthenticationsHigh  OBJECT-TYPE
	SYNTAX  Counter32
	MAX-ACCESS  read-only
	STATUS  obsolete
	DESCRIPTION
		"...OBSOLETE"
	::= { nsSslStatsGroup 48 }

sslTotSSLv3ClientAuthenticationsLow  OBJECT-TYPE
	SYNTAX  Counter32
	MAX-ACCESS  read-only
	STATUS  obsolete
	DESCRIPTION
		"...OBSOLETE"
	::= { nsSslStatsGroup 49 }

sslTotSSLv3ClientAuthenticationsHigh  OBJECT-TYPE
	SYNTAX  Counter32
	MAX-ACCESS  read-only
	STATUS  obsolete
	DESCRIPTION
		"...OBSOLETE"
	::= { nsSslStatsGroup 50 }

sslTotTLSv1ClientAuthenticationsLow  OBJECT-TYPE
	SYNTAX  Counter32
	MAX-ACCESS  read-only
	STATUS  obsolete
	DESCRIPTION
		"...OBSOLETE"
	::= { nsSslStatsGroup 51 }

sslTotTLSv1ClientAuthenticationsHigh  OBJECT-TYPE
	SYNTAX  Counter32
	MAX-ACCESS  read-only
	STATUS  obsolete
	DESCRIPTION
		"...OBSOLETE"
	::= { nsSslStatsGroup 52 }

sslTotRSA512keyExchangesLow  OBJECT-TYPE
	SYNTAX  Counter32
	MAX-ACCESS  read-only
	STATUS  obsolete
	DESCRIPTION
		"...OBSOLETE"
	::= { nsSslStatsGroup 53 }

sslTotRSA512keyExchangesHigh  OBJECT-TYPE
	SYNTAX  Counter32
	MAX-ACCESS  read-only
	STATUS  obsolete
	DESCRIPTION
		"...OBSOLETE"
	::= { nsSslStatsGroup 54 }

sslTotRSA1024keyExchangesLow  OBJECT-TYPE
	SYNTAX  Counter32
	MAX-ACCESS  read-only
	STATUS  obsolete
	DESCRIPTION
		"...OBSOLETE"
	::= { nsSslStatsGroup 55 }

sslTotRSA1024keyExchangesHigh  OBJECT-TYPE
	SYNTAX  Counter32
	MAX-ACCESS  read-only
	STATUS  obsolete
	DESCRIPTION
		"...OBSOLETE"
	::= { nsSslStatsGroup 56 }

sslTotRSA2048keyExchangesLow  OBJECT-TYPE
	SYNTAX  Counter32
	MAX-ACCESS  read-only
	STATUS  obsolete
	DESCRIPTION
		"...OBSOLETE"
	::= { nsSslStatsGroup 57 }

sslTotRSA2048keyExchangesHigh  OBJECT-TYPE
	SYNTAX  Counter32
	MAX-ACCESS  read-only
	STATUS  obsolete
	DESCRIPTION
		"...OBSOLETE"
	::= { nsSslStatsGroup 58 }

sslTotDH512keyExchangesLow  OBJECT-TYPE
	SYNTAX  Counter32
	MAX-ACCESS  read-only
	STATUS  obsolete
	DESCRIPTION
		"...OBSOLETE"
	::= { nsSslStatsGroup 59 }

sslTotDH512keyExchangesHigh  OBJECT-TYPE
	SYNTAX  Counter32
	MAX-ACCESS  read-only
	STATUS  obsolete
	DESCRIPTION
		"...OBSOLETE"
	::= { nsSslStatsGroup 60 }

sslTotDH1024keyExchangesLow  OBJECT-TYPE
	SYNTAX  Counter32
	MAX-ACCESS  read-only
	STATUS  obsolete
	DESCRIPTION
		"...OBSOLETE"
	::= { nsSslStatsGroup 61 }

sslTotDH1024keyExchangesHigh  OBJECT-TYPE
	SYNTAX  Counter32
	MAX-ACCESS  read-only
	STATUS  obsolete
	DESCRIPTION
		"...OBSOLETE"
	::= { nsSslStatsGroup 62 }

sslTotDH2048keyExchangesLow  OBJECT-TYPE
	SYNTAX  Counter32
	MAX-ACCESS  read-only
	STATUS  obsolete
	DESCRIPTION
		"...OBSOLETE"
	::= { nsSslStatsGroup 63 }

sslTotDH2048keyExchangesHigh  OBJECT-TYPE
	SYNTAX  Counter32
	MAX-ACCESS  read-only
	STATUS  obsolete
	DESCRIPTION
		"...OBSOLETE"
	::= { nsSslStatsGroup 64 }

sslTotRSAAuthorizationsLow  OBJECT-TYPE
	SYNTAX  Counter32
	MAX-ACCESS  read-only
	STATUS  obsolete
	DESCRIPTION
		"...OBSOLETE"
	::= { nsSslStatsGroup 65 }

sslTotRSAAuthorizationsHigh  OBJECT-TYPE
	SYNTAX  Counter32
	MAX-ACCESS  read-only
	STATUS  obsolete
	DESCRIPTION
		"...OBSOLETE"
	::= { nsSslStatsGroup 66 }

sslTotDHAuthorizationsLow  OBJECT-TYPE
	SYNTAX  Counter32
	MAX-ACCESS  read-only
	STATUS  obsolete
	DESCRIPTION
		"...OBSOLETE"
	::= { nsSslStatsGroup 67 }

sslTotDHAuthorizationsHigh  OBJECT-TYPE
	SYNTAX  Counter32
	MAX-ACCESS  read-only
	STATUS  obsolete
	DESCRIPTION
		"...OBSOLETE"
	::= { nsSslStatsGroup 68 }

sslTotDSSAuthorizationsLow  OBJECT-TYPE
	SYNTAX  Counter32
	MAX-ACCESS  read-only
	STATUS  obsolete
	DESCRIPTION
		"...OBSOLETE"
	::= { nsSslStatsGroup 69 }

sslTotDSSAuthorizationsHigh  OBJECT-TYPE
	SYNTAX  Counter32
	MAX-ACCESS  read-only
	STATUS  obsolete
	DESCRIPTION
		"...OBSOLETE"
	::= { nsSslStatsGroup 70 }

sslTotNULLAuthorizationsLow  OBJECT-TYPE
	SYNTAX  Counter32
	MAX-ACCESS  read-only
	STATUS  obsolete
	DESCRIPTION
		"...OBSOLETE"
	::= { nsSslStatsGroup 71 }

sslTotNULLAuthorizationsHigh  OBJECT-TYPE
	SYNTAX  Counter32
	MAX-ACCESS  read-only
	STATUS  obsolete
	DESCRIPTION
		"...OBSOLETE"
	::= { nsSslStatsGroup 72 }

sslTot40BitRC4CiphersLow  OBJECT-TYPE
	SYNTAX  Counter32
	MAX-ACCESS  read-only
	STATUS  obsolete
	DESCRIPTION
		"...OBSOLETE"
	::= { nsSslStatsGroup 73 }

sslTot40BitRC4CiphersHigh  OBJECT-TYPE
	SYNTAX  Counter32
	MAX-ACCESS  read-only
	STATUS  obsolete
	DESCRIPTION
		"...OBSOLETE"
	::= { nsSslStatsGroup 74 }

sslTot56BitRC4CiphersLow  OBJECT-TYPE
	SYNTAX  Counter32
	MAX-ACCESS  read-only
	STATUS  obsolete
	DESCRIPTION
		"...OBSOLETE"
	::= { nsSslStatsGroup 75 }

sslTot56BitRC4CiphersHigh  OBJECT-TYPE
	SYNTAX  Counter32
	MAX-ACCESS  read-only
	STATUS  obsolete
	DESCRIPTION
		"...OBSOLETE"
	::= { nsSslStatsGroup 76 }

sslTot64BitRC4CiphersLow  OBJECT-TYPE
	SYNTAX  Counter32
	MAX-ACCESS  read-only
	STATUS  obsolete
	DESCRIPTION
		"...OBSOLETE"
	::= { nsSslStatsGroup 77 }

sslTot64BitRC4CiphersHigh  OBJECT-TYPE
	SYNTAX  Counter32
	MAX-ACCESS  read-only
	STATUS  obsolete
	DESCRIPTION
		"...OBSOLETE"
	::= { nsSslStatsGroup 78 }

sslTot128BitRC4CiphersLow  OBJECT-TYPE
	SYNTAX  Counter32
	MAX-ACCESS  read-only
	STATUS  obsolete
	DESCRIPTION
		"...OBSOLETE"
	::= { nsSslStatsGroup 79 }

sslTot128BitRC4CiphersHigh  OBJECT-TYPE
	SYNTAX  Counter32
	MAX-ACCESS  read-only
	STATUS  obsolete
	DESCRIPTION
		"...OBSOLETE"
	::= { nsSslStatsGroup 80 }

sslTot40BitDESCiphersLow  OBJECT-TYPE
	SYNTAX  Counter32
	MAX-ACCESS  read-only
	STATUS  obsolete
	DESCRIPTION
		"...OBSOLETE"
	::= { nsSslStatsGroup 81 }

sslTot40BitDESCiphersHigh  OBJECT-TYPE
	SYNTAX  Counter32
	MAX-ACCESS  read-only
	STATUS  obsolete
	DESCRIPTION
		"...OBSOLETE"
	::= { nsSslStatsGroup 82 }

sslTot56BitDESCiphersLow  OBJECT-TYPE
	SYNTAX  Counter32
	MAX-ACCESS  read-only
	STATUS  obsolete
	DESCRIPTION
		"...OBSOLETE"
	::= { nsSslStatsGroup 83 }

sslTot56BitDESCiphersHigh  OBJECT-TYPE
	SYNTAX  Counter32
	MAX-ACCESS  read-only
	STATUS  obsolete
	DESCRIPTION
		"...OBSOLETE"
	::= { nsSslStatsGroup 84 }

sslTot168Bit3DESCiphersLow  OBJECT-TYPE
	SYNTAX  Counter32
	MAX-ACCESS  read-only
	STATUS  obsolete
	DESCRIPTION
		"...OBSOLETE"
	::= { nsSslStatsGroup 85 }

sslTot168Bit3DESCiphersHigh  OBJECT-TYPE
	SYNTAX  Counter32
	MAX-ACCESS  read-only
	STATUS  obsolete
	DESCRIPTION
		"...OBSOLETE"
	::= { nsSslStatsGroup 86 }

sslTot40BitRC2CiphersLow  OBJECT-TYPE
	SYNTAX  Counter32
	MAX-ACCESS  read-only
	STATUS  obsolete
	DESCRIPTION
		"...OBSOLETE"
	::= { nsSslStatsGroup 87 }

sslTot40BitRC2CiphersHigh  OBJECT-TYPE
	SYNTAX  Counter32
	MAX-ACCESS  read-only
	STATUS  obsolete
	DESCRIPTION
		"...OBSOLETE"
	::= { nsSslStatsGroup 88 }

sslTot56BitRC2CiphersLow  OBJECT-TYPE
	SYNTAX  Counter32
	MAX-ACCESS  read-only
	STATUS  obsolete
	DESCRIPTION
		"...OBSOLETE"
	::= { nsSslStatsGroup 89 }

sslTot56BitRC2CiphersHigh  OBJECT-TYPE
	SYNTAX  Counter32
	MAX-ACCESS  read-only
	STATUS  obsolete
	DESCRIPTION
		"...OBSOLETE"
	::= { nsSslStatsGroup 90 }

sslTot128BitRC2CiphersLow  OBJECT-TYPE
	SYNTAX  Counter32
	MAX-ACCESS  read-only
	STATUS  obsolete
	DESCRIPTION
		"...OBSOLETE"
	::= { nsSslStatsGroup 91 }

sslTot128BitRC2CiphersHigh  OBJECT-TYPE
	SYNTAX  Counter32
	MAX-ACCESS  read-only
	STATUS  obsolete
	DESCRIPTION
		"...OBSOLETE"
	::= { nsSslStatsGroup 92 }

sslTot128BitIDEACiphersLow  OBJECT-TYPE
	SYNTAX  Counter32
	MAX-ACCESS  read-only
	STATUS  obsolete
	DESCRIPTION
		"...OBSOLETE"
	::= { nsSslStatsGroup 93 }

sslTot128BitIDEACiphersHigh  OBJECT-TYPE
	SYNTAX  Counter32
	MAX-ACCESS  read-only
	STATUS  obsolete
	DESCRIPTION
		"...OBSOLETE"
	::= { nsSslStatsGroup 94 }

sslTotNULLCiphersLow  OBJECT-TYPE
	SYNTAX  Counter32
	MAX-ACCESS  read-only
	STATUS  obsolete
	DESCRIPTION
		"...OBSOLETE"
	::= { nsSslStatsGroup 95 }

sslTotNULLCiphersHigh  OBJECT-TYPE
	SYNTAX  Counter32
	MAX-ACCESS  read-only
	STATUS  obsolete
	DESCRIPTION
		"...OBSOLETE"
	::= { nsSslStatsGroup 96 }

sslTotMD5MacLow  OBJECT-TYPE
	SYNTAX  Counter32
	MAX-ACCESS  read-only
	STATUS  obsolete
	DESCRIPTION
		"...OBSOLETE"
	::= { nsSslStatsGroup 97 }

sslTotMD5MacHigh  OBJECT-TYPE
	SYNTAX  Counter32
	MAX-ACCESS  read-only
	STATUS  obsolete
	DESCRIPTION
		"...OBSOLETE"
	::= { nsSslStatsGroup 98 }

sslTotSHAMacLow  OBJECT-TYPE
	SYNTAX  Counter32
	MAX-ACCESS  read-only
	STATUS  obsolete
	DESCRIPTION
		"...OBSOLETE"
	::= { nsSslStatsGroup 99 }

sslTotSHAMacHigh  OBJECT-TYPE
	SYNTAX  Counter32
	MAX-ACCESS  read-only
	STATUS  obsolete
	DESCRIPTION
		"...OBSOLETE"
	::= { nsSslStatsGroup 100 }

sslTotOffloadBulkDESLow  OBJECT-TYPE
	SYNTAX  Counter32
	MAX-ACCESS  read-only
	STATUS  obsolete
	DESCRIPTION
		"...OBSOLETE"
	::= { nsSslStatsGroup 101 }

sslTotOffloadBulkDESHigh  OBJECT-TYPE
	SYNTAX  Counter32
	MAX-ACCESS  read-only
	STATUS  obsolete
	DESCRIPTION
		"...OBSOLETE"
	::= { nsSslStatsGroup 102 }

sslTotOffloadRSAKeyExchangesLow  OBJECT-TYPE
	SYNTAX  Counter32
	MAX-ACCESS  read-only
	STATUS  obsolete
	DESCRIPTION
		"...OBSOLETE"
	::= { nsSslStatsGroup 103 }

sslTotOffloadRSAKeyExchangesHigh  OBJECT-TYPE
	SYNTAX  Counter32
	MAX-ACCESS  read-only
	STATUS  obsolete
	DESCRIPTION
		"...OBSOLETE"
	::= { nsSslStatsGroup 104 }

sslTotOffloadDHKeyExchangesLow  OBJECT-TYPE
	SYNTAX  Counter32
	MAX-ACCESS  read-only
	STATUS  obsolete
	DESCRIPTION
		"...OBSOLETE"
	::= { nsSslStatsGroup 105 }

sslTotOffloadDHKeyExchangesHigh  OBJECT-TYPE
	SYNTAX  Counter32
	MAX-ACCESS  read-only
	STATUS  obsolete
	DESCRIPTION
		"...OBSOLETE"
	::= { nsSslStatsGroup 106 }

sslTotOffloadSignRSALow  OBJECT-TYPE
	SYNTAX  Counter32
	MAX-ACCESS  read-only
	STATUS  obsolete
	DESCRIPTION
		"...OBSOLETE"
	::= { nsSslStatsGroup 107 }

sslTotOffloadSignRSAHigh  OBJECT-TYPE
	SYNTAX  Counter32
	MAX-ACCESS  read-only
	STATUS  obsolete
	DESCRIPTION
		"...OBSOLETE"
	::= { nsSslStatsGroup 108 }

sslBeTotSessionsLow  OBJECT-TYPE
	SYNTAX  Counter32
	MAX-ACCESS  read-only
	STATUS  obsolete
	DESCRIPTION
		"...OBSOLETE"
	::= { nsSslStatsGroup 120 }

sslBeTotSessionsHigh  OBJECT-TYPE
	SYNTAX  Counter32
	MAX-ACCESS  read-only
	STATUS  obsolete
	DESCRIPTION
		"...OBSOLETE"
	::= { nsSslStatsGroup 121 }

sslBeTotSSLv3SessionsLow  OBJECT-TYPE
	SYNTAX  Counter32
	MAX-ACCESS  read-only
	STATUS  obsolete
	DESCRIPTION
		"...OBSOLETE"
	::= { nsSslStatsGroup 122 }

sslBeTotSSLv3SessionsHigh  OBJECT-TYPE
	SYNTAX  Counter32
	MAX-ACCESS  read-only
	STATUS  obsolete
	DESCRIPTION
		"...OBSOLETE"
	::= { nsSslStatsGroup 123 }

sslBeTotTLSv1SessionsLow  OBJECT-TYPE
	SYNTAX  Counter32
	MAX-ACCESS  read-only
	STATUS  obsolete
	DESCRIPTION
		"...OBSOLETE"
	::= { nsSslStatsGroup 124 }

sslBeTotTLSv1SessionsHigh  OBJECT-TYPE
	SYNTAX  Counter32
	MAX-ACCESS  read-only
	STATUS  obsolete
	DESCRIPTION
		"...OBSOLETE"
	::= { nsSslStatsGroup 125 }

sslBeExpiredSessionsLow  OBJECT-TYPE
	SYNTAX  Counter32
	MAX-ACCESS  read-only
	STATUS  obsolete
	DESCRIPTION
		"...OBSOLETE"
	::= { nsSslStatsGroup 126 }

sslBeTotExpiredSessionsHigh  OBJECT-TYPE
	SYNTAX  Counter32
	MAX-ACCESS  read-only
	STATUS  obsolete
	DESCRIPTION
		"...OBSOLETE"
	::= { nsSslStatsGroup 127 }

sslBeTotSessionMultiplexAttemptsLow  OBJECT-TYPE
	SYNTAX  Counter32
	MAX-ACCESS  read-only
	STATUS  obsolete
	DESCRIPTION
		"...OBSOLETE"
	::= { nsSslStatsGroup 128 }

sslBeTotSessionMultiplexAttemptsHigh  OBJECT-TYPE
	SYNTAX  Counter32
	MAX-ACCESS  read-only
	STATUS  obsolete
	DESCRIPTION
		"...OBSOLETE"
	::= { nsSslStatsGroup 129 }

sslBeTotSessionMultiplexAttemptSuccessLow  OBJECT-TYPE
	SYNTAX  Counter32
	MAX-ACCESS  read-only
	STATUS  obsolete
	DESCRIPTION
		"...OBSOLETE"
	::= { nsSslStatsGroup 130 }

sslBeTotSessionMultiplexAttemptSuccessHigh  OBJECT-TYPE
	SYNTAX  Counter32
	MAX-ACCESS  read-only
	STATUS  obsolete
	DESCRIPTION
		"...OBSOLETE"
	::= { nsSslStatsGroup 131 }

sslBeTotSessionMultiplexAttemptFailsLow  OBJECT-TYPE
	SYNTAX  Counter32
	MAX-ACCESS  read-only
	STATUS  obsolete
	DESCRIPTION
		"...OBSOLETE"
	::= { nsSslStatsGroup 132 }

sslBeTotSessionMultiplexAttemptFailsHigh  OBJECT-TYPE
	SYNTAX  Counter32
	MAX-ACCESS  read-only
	STATUS  obsolete
	DESCRIPTION
		"...OBSOLETE"
	::= { nsSslStatsGroup 133 }

sslBeMaxMultiplexedSessionsLow  OBJECT-TYPE
	SYNTAX  Counter32
	MAX-ACCESS  read-only
	STATUS  obsolete
	DESCRIPTION
		"...OBSOLETE"
	::= { nsSslStatsGroup 134 }

sslBeMaxMultiplexedSessionsHigh  OBJECT-TYPE
	SYNTAX  Counter32
	MAX-ACCESS  read-only
	STATUS  obsolete
	DESCRIPTION
		"...OBSOLETE"
	::= { nsSslStatsGroup 135 }

sslBeSessionsReplacedLow  OBJECT-TYPE
	SYNTAX  Counter32
	MAX-ACCESS  read-only
	STATUS  obsolete
	DESCRIPTION
		"...OBSOLETE"
	::= { nsSslStatsGroup 136 }

sslBeSessionsReplacedHigh  OBJECT-TYPE
	SYNTAX  Counter32
	MAX-ACCESS  read-only
	STATUS  obsolete
	DESCRIPTION
		"...OBSOLETE"
	::= { nsSslStatsGroup 137 }

sslBeTotSSLv3HandshakesLow  OBJECT-TYPE
	SYNTAX  Counter32
	MAX-ACCESS  read-only
	STATUS  obsolete
	DESCRIPTION
		"...OBSOLETE"
	::= { nsSslStatsGroup 138 }

sslBeTotSSLv3HandshakesHigh  OBJECT-TYPE
	SYNTAX  Counter32
	MAX-ACCESS  read-only
	STATUS  obsolete
	DESCRIPTION
		"...OBSOLETE"
	::= { nsSslStatsGroup 139 }

sslBeTotTLSv1HandshakesLow  OBJECT-TYPE
	SYNTAX  Counter32
	MAX-ACCESS  read-only
	STATUS  obsolete
	DESCRIPTION
		"...OBSOLETE"
	::= { nsSslStatsGroup 140 }

sslBeTotTLSv1HandshakesHigh  OBJECT-TYPE
	SYNTAX  Counter32
	MAX-ACCESS  read-only
	STATUS  obsolete
	DESCRIPTION
		"...OBSOLETE"
	::= { nsSslStatsGroup 141 }

sslBeTotSSLv3ClientAuthenticationsLow  OBJECT-TYPE
	SYNTAX  Counter32
	MAX-ACCESS  read-only
	STATUS  obsolete
	DESCRIPTION
		"...OBSOLETE"
	::= { nsSslStatsGroup 142 }

sslBeTotSSLv3ClientAuthenticationsHigh  OBJECT-TYPE
	SYNTAX  Counter32
	MAX-ACCESS  read-only
	STATUS  obsolete
	DESCRIPTION
		"...OBSOLETE"
	::= { nsSslStatsGroup 143 }

sslBeTotTLSv1ClientAuthenticationsLow  OBJECT-TYPE
	SYNTAX  Counter32
	MAX-ACCESS  read-only
	STATUS  obsolete
	DESCRIPTION
		"...OBSOLETE"
	::= { nsSslStatsGroup 144 }

sslBeTotTLSv1ClientAuthenticationsHigh  OBJECT-TYPE
	SYNTAX  Counter32
	MAX-ACCESS  read-only
	STATUS  obsolete
	DESCRIPTION
		"...OBSOLETE"
	::= { nsSslStatsGroup 145 }

sslBeTotRSA512keyExchangesLow  OBJECT-TYPE
	SYNTAX  Counter32
	MAX-ACCESS  read-only
	STATUS  obsolete
	DESCRIPTION
		"...OBSOLETE"
	::= { nsSslStatsGroup 146 }

sslBeTotRSA512keyExchangesHigh  OBJECT-TYPE
	SYNTAX  Counter32
	MAX-ACCESS  read-only
	STATUS  obsolete
	DESCRIPTION
		"...OBSOLETE"
	::= { nsSslStatsGroup 147 }

sslBeTotRSA1024keyExchangesLow  OBJECT-TYPE
	SYNTAX  Counter32
	MAX-ACCESS  read-only
	STATUS  obsolete
	DESCRIPTION
		"...OBSOLETE"
	::= { nsSslStatsGroup 148 }

sslBeTotRSA1024keyExchangesHigh  OBJECT-TYPE
	SYNTAX  Counter32
	MAX-ACCESS  read-only
	STATUS  obsolete
	DESCRIPTION
		"...OBSOLETE"
	::= { nsSslStatsGroup 149 }

sslBeTotRSA2048keyExchangesLow  OBJECT-TYPE
	SYNTAX  Counter32
	MAX-ACCESS  read-only
	STATUS  obsolete
	DESCRIPTION
		"...OBSOLETE"
	::= { nsSslStatsGroup 150 }

sslBeTotRSA2048keyExchangesHigh  OBJECT-TYPE
	SYNTAX  Counter32
	MAX-ACCESS  read-only
	STATUS  obsolete
	DESCRIPTION
		"...OBSOLETE"
	::= { nsSslStatsGroup 151 }

sslBeTotDH512keyExchangesLow  OBJECT-TYPE
	SYNTAX  Counter32
	MAX-ACCESS  read-only
	STATUS  obsolete
	DESCRIPTION
		"...OBSOLETE"
	::= { nsSslStatsGroup 152 }

sslBeTotDH512keyExchangesHigh  OBJECT-TYPE
	SYNTAX  Counter32
	MAX-ACCESS  read-only
	STATUS  obsolete
	DESCRIPTION
		"...OBSOLETE"
	::= { nsSslStatsGroup 153 }

sslBeTotDH1024keyExchangesLow  OBJECT-TYPE
	SYNTAX  Counter32
	MAX-ACCESS  read-only
	STATUS  obsolete
	DESCRIPTION
		"...OBSOLETE"
	::= { nsSslStatsGroup 154 }

sslBeTotDH1024keyExchangesHigh  OBJECT-TYPE
	SYNTAX  Counter32
	MAX-ACCESS  read-only
	STATUS  obsolete
	DESCRIPTION
		"...OBSOLETE"
	::= { nsSslStatsGroup 155 }

sslBeTotDH2048keyExchangesLow  OBJECT-TYPE
	SYNTAX  Counter32
	MAX-ACCESS  read-only
	STATUS  obsolete
	DESCRIPTION
		"...OBSOLETE"
	::= { nsSslStatsGroup 156 }

sslBeTotDH2048keyExchangesHigh  OBJECT-TYPE
	SYNTAX  Counter32
	MAX-ACCESS  read-only
	STATUS  obsolete
	DESCRIPTION
		"...OBSOLETE"
	::= { nsSslStatsGroup 157 }

sslBeTotRSAAuthorizationsLow  OBJECT-TYPE
	SYNTAX  Counter32
	MAX-ACCESS  read-only
	STATUS  obsolete
	DESCRIPTION
		"...OBSOLETE"
	::= { nsSslStatsGroup 158 }

sslBeTotRSAAuthorizationsHigh  OBJECT-TYPE
	SYNTAX  Counter32
	MAX-ACCESS  read-only
	STATUS  obsolete
	DESCRIPTION
		"...OBSOLETE"
	::= { nsSslStatsGroup 159 }

sslBeTotDHAuthorizationsLow  OBJECT-TYPE
	SYNTAX  Counter32
	MAX-ACCESS  read-only
	STATUS  obsolete
	DESCRIPTION
		"...OBSOLETE"
	::= { nsSslStatsGroup 160 }

sslBeTotDHAuthorizationsHigh  OBJECT-TYPE
	SYNTAX  Counter32
	MAX-ACCESS  read-only
	STATUS  obsolete
	DESCRIPTION
		"...OBSOLETE"
	::= { nsSslStatsGroup 161 }

sslBeTotDSSAuthorizationsLow  OBJECT-TYPE
	SYNTAX  Counter32
	MAX-ACCESS  read-only
	STATUS  obsolete
	DESCRIPTION
		"...OBSOLETE"
	::= { nsSslStatsGroup 162 }

sslBeTotDSSAuthorizationsHigh  OBJECT-TYPE
	SYNTAX  Counter32
	MAX-ACCESS  read-only
	STATUS  obsolete
	DESCRIPTION
		"...OBSOLETE"
	::= { nsSslStatsGroup 163 }

sslBeTotNULLAuthorizationsLow  OBJECT-TYPE
	SYNTAX  Counter32
	MAX-ACCESS  read-only
	STATUS  obsolete
	DESCRIPTION
		"...OBSOLETE"
	::= { nsSslStatsGroup 164 }

sslBeTotNULLAuthorizationsHigh  OBJECT-TYPE
	SYNTAX  Counter32
	MAX-ACCESS  read-only
	STATUS  obsolete
	DESCRIPTION
		"...OBSOLETE"
	::= { nsSslStatsGroup 165 }

sslBeTot40BitRC4CiphersLow  OBJECT-TYPE
	SYNTAX  Counter32
	MAX-ACCESS  read-only
	STATUS  obsolete
	DESCRIPTION
		"...OBSOLETE"
	::= { nsSslStatsGroup 166 }

sslBeTot40BitRC4CiphersHigh  OBJECT-TYPE
	SYNTAX  Counter32
	MAX-ACCESS  read-only
	STATUS  obsolete
	DESCRIPTION
		"...OBSOLETE"
	::= { nsSslStatsGroup 167 }

sslBeTot56BitRC4CiphersLow  OBJECT-TYPE
	SYNTAX  Counter32
	MAX-ACCESS  read-only
	STATUS  obsolete
	DESCRIPTION
		"...OBSOLETE"
	::= { nsSslStatsGroup 168 }

sslBeTot56BitRC4CiphersHigh  OBJECT-TYPE
	SYNTAX  Counter32
	MAX-ACCESS  read-only
	STATUS  obsolete
	DESCRIPTION
		"...OBSOLETE"
	::= { nsSslStatsGroup 169 }

sslBeTot64BitRC4CiphersLow  OBJECT-TYPE
	SYNTAX  Counter32
	MAX-ACCESS  read-only
	STATUS  obsolete
	DESCRIPTION
		"...OBSOLETE"
	::= { nsSslStatsGroup 170 }

sslBeTot64BitRC4CiphersHigh  OBJECT-TYPE
	SYNTAX  Counter32
	MAX-ACCESS  read-only
	STATUS  obsolete
	DESCRIPTION
		"...OBSOLETE"
	::= { nsSslStatsGroup 171 }

sslBeTot128BitRC4CiphersLow  OBJECT-TYPE
	SYNTAX  Counter32
	MAX-ACCESS  read-only
	STATUS  obsolete
	DESCRIPTION
		"...OBSOLETE"
	::= { nsSslStatsGroup 172 }

sslBeTot128BitRC4CiphersHigh  OBJECT-TYPE
	SYNTAX  Counter32
	MAX-ACCESS  read-only
	STATUS  obsolete
	DESCRIPTION
		"...OBSOLETE"
	::= { nsSslStatsGroup 173 }

sslBeTot40BitDESCiphersLow  OBJECT-TYPE
	SYNTAX  Counter32
	MAX-ACCESS  read-only
	STATUS  obsolete
	DESCRIPTION
		"...OBSOLETE"
	::= { nsSslStatsGroup 174 }

sslBeTot40BitDESCiphersHigh  OBJECT-TYPE
	SYNTAX  Counter32
	MAX-ACCESS  read-only
	STATUS  obsolete
	DESCRIPTION
		"...OBSOLETE"
	::= { nsSslStatsGroup 175 }

sslBeTot56BitDESCiphersLow  OBJECT-TYPE
	SYNTAX  Counter32
	MAX-ACCESS  read-only
	STATUS  obsolete
	DESCRIPTION
		"...OBSOLETE"
	::= { nsSslStatsGroup 176 }

sslBeTot56BitDESCiphersHigh  OBJECT-TYPE
	SYNTAX  Counter32
	MAX-ACCESS  read-only
	STATUS  obsolete
	DESCRIPTION
		"...OBSOLETE"
	::= { nsSslStatsGroup 177 }

sslBeTot168Bit3DESCiphersLow  OBJECT-TYPE
	SYNTAX  Counter32
	MAX-ACCESS  read-only
	STATUS  obsolete
	DESCRIPTION
		"...OBSOLETE"
	::= { nsSslStatsGroup 178 }

sslBeTot168Bit3DESCiphersHigh  OBJECT-TYPE
	SYNTAX  Counter32
	MAX-ACCESS  read-only
	STATUS  obsolete
	DESCRIPTION
		"...OBSOLETE"
	::= { nsSslStatsGroup 179 }

sslBeTot40BitRC2CiphersLow  OBJECT-TYPE
	SYNTAX  Counter32
	MAX-ACCESS  read-only
	STATUS  obsolete
	DESCRIPTION
		"...OBSOLETE"
	::= { nsSslStatsGroup 180 }

sslBeTot40BitRC2CiphersHigh  OBJECT-TYPE
	SYNTAX  Counter32
	MAX-ACCESS  read-only
	STATUS  obsolete
	DESCRIPTION
		"...OBSOLETE"
	::= { nsSslStatsGroup 181 }

sslBeTot56BitRC2CiphersLow  OBJECT-TYPE
	SYNTAX  Counter32
	MAX-ACCESS  read-only
	STATUS  obsolete
	DESCRIPTION
		"...OBSOLETE"
	::= { nsSslStatsGroup 182 }

sslBeTot56BitRC2CiphersHigh  OBJECT-TYPE
	SYNTAX  Counter32
	MAX-ACCESS  read-only
	STATUS  obsolete
	DESCRIPTION
		"...OBSOLETE"
	::= { nsSslStatsGroup 183 }

sslBeTot128BitRC2CiphersLow  OBJECT-TYPE
	SYNTAX  Counter32
	MAX-ACCESS  read-only
	STATUS  obsolete
	DESCRIPTION
		"...OBSOLETE"
	::= { nsSslStatsGroup 184 }

sslBeTot128BitRC2CiphersHigh  OBJECT-TYPE
	SYNTAX  Counter32
	MAX-ACCESS  read-only
	STATUS  obsolete
	DESCRIPTION
		"...OBSOLETE"
	::= { nsSslStatsGroup 185 }

sslBeTot128BitIDEACiphersLow  OBJECT-TYPE
	SYNTAX  Counter32
	MAX-ACCESS  read-only
	STATUS  obsolete
	DESCRIPTION
		"...OBSOLETE"
	::= { nsSslStatsGroup 186 }

sslBeTot128BitIDEACiphersHigh  OBJECT-TYPE
	SYNTAX  Counter32
	MAX-ACCESS  read-only
	STATUS  obsolete
	DESCRIPTION
		"...OBSOLETE"
	::= { nsSslStatsGroup 187 }

sslBeTotNULLCiphersLow  OBJECT-TYPE
	SYNTAX  Counter32
	MAX-ACCESS  read-only
	STATUS  obsolete
	DESCRIPTION
		"...OBSOLETE"
	::= { nsSslStatsGroup 188 }

sslBeTotNULLCiphersHigh  OBJECT-TYPE
	SYNTAX  Counter32
	MAX-ACCESS  read-only
	STATUS  obsolete
	DESCRIPTION
		"...OBSOLETE"
	::= { nsSslStatsGroup 189 }

sslBeTotMD5MacLow  OBJECT-TYPE
	SYNTAX  Counter32
	MAX-ACCESS  read-only
	STATUS  obsolete
	DESCRIPTION
		"...OBSOLETE"
	::= { nsSslStatsGroup 190 }

sslBeTotMD5MacHigh  OBJECT-TYPE
	SYNTAX  Counter32
	MAX-ACCESS  read-only
	STATUS  obsolete
	DESCRIPTION
		"...OBSOLETE"
	::= { nsSslStatsGroup 191 }

sslBeTotSHAMacLow  OBJECT-TYPE
	SYNTAX  Counter32
	MAX-ACCESS  read-only
	STATUS  obsolete
	DESCRIPTION
		"...OBSOLETE"
	::= { nsSslStatsGroup 192 }

sslBeTotSHAMacHigh  OBJECT-TYPE
	SYNTAX  Counter32
	MAX-ACCESS  read-only
	STATUS  obsolete
	DESCRIPTION
		"...OBSOLETE"
	::= { nsSslStatsGroup 193 }

sslTotTransactions  OBJECT-TYPE
	SYNTAX  Counter64
	MAX-ACCESS  read-only
	STATUS  current
	DESCRIPTION
		"Number of SSL transactions"
	::= { nsSslStatsGroup 200 }

sslTotSSLv2Transactions  OBJECT-TYPE
	SYNTAX  Counter64
	MAX-ACCESS  read-only
	STATUS  current
	DESCRIPTION
		"Number of SSLv2 transactions"
	::= { nsSslStatsGroup 201 }

sslTotSSLv3Transactions  OBJECT-TYPE
	SYNTAX  Counter64
	MAX-ACCESS  read-only
	STATUS  current
	DESCRIPTION
		" Total number of SSLv3 Transactions. "
	::= { nsSslStatsGroup 202 }

sslTotTLSv1Transactions  OBJECT-TYPE
	SYNTAX  Counter64
	MAX-ACCESS  read-only
	STATUS  current
	DESCRIPTION
		"Number of TLSv1 transactions"
	::= { nsSslStatsGroup 203 }

sslTotSessions  OBJECT-TYPE
	SYNTAX  Counter64
	MAX-ACCESS  read-only
	STATUS  current
	DESCRIPTION
		"Number of SSL sessions"
	::= { nsSslStatsGroup 204 }

sslTotSSLv2Sessions  OBJECT-TYPE
	SYNTAX  Counter64
	MAX-ACCESS  read-only
	STATUS  current
	DESCRIPTION
		"Number of SSLv2 sessions"
	::= { nsSslStatsGroup 205 }

sslTotSSLv3Sessions  OBJECT-TYPE
	SYNTAX  Counter64
	MAX-ACCESS  read-only
	STATUS  current
	DESCRIPTION
		"Number of SSLv3 sessions"
	::= { nsSslStatsGroup 206 }

sslTotTLSv1Sessions  OBJECT-TYPE
	SYNTAX  Counter64
	MAX-ACCESS  read-only
	STATUS  current
	DESCRIPTION
		"Number of TLSv1 sessions"
	::= { nsSslStatsGroup 207 }

sslTotExpiredSessions  OBJECT-TYPE
	SYNTAX  Counter64
	MAX-ACCESS  read-only
	STATUS  current
	DESCRIPTION
		"Total number of Expired SSL Sessions."
	::= { nsSslStatsGroup 208 }

sslTotNewSessions  OBJECT-TYPE
	SYNTAX  Counter64
	MAX-ACCESS  read-only
	STATUS  current
	DESCRIPTION
		"Number of new SSL sessions created."
	::= { nsSslStatsGroup 209 }

sslTotSessionHits  OBJECT-TYPE
	SYNTAX  Counter64
	MAX-ACCESS  read-only
	STATUS  current
	DESCRIPTION
		"Number of SSL session reuse hits"
	::= { nsSslStatsGroup 210 }

sslTotSessionMiss  OBJECT-TYPE
	SYNTAX  Counter64
	MAX-ACCESS  read-only
	STATUS  current
	DESCRIPTION
		"Number of SSL session reuse misses"
	::= { nsSslStatsGroup 211 }

sslTotRenegSessions  OBJECT-TYPE
	SYNTAX  Counter64
	MAX-ACCESS  read-only
	STATUS  current
	DESCRIPTION
		"Number of SSL session renegotiations"
	::= { nsSslStatsGroup 212 }

sslTotSSLv3RenegSessions  OBJECT-TYPE
	SYNTAX  Counter64
	MAX-ACCESS  read-only
	STATUS  current
	DESCRIPTION
		"Number of session renegotiations done on SSLv3"
	::= { nsSslStatsGroup 213 }

sslTotTLSv1RenegSessions  OBJECT-TYPE
	SYNTAX  Counter64
	MAX-ACCESS  read-only
	STATUS  current
	DESCRIPTION
		"Number of SSL session renegotiations done on TLSv1"
	::= { nsSslStatsGroup 214 }

sslTotSSLv2Handshakes  OBJECT-TYPE
	SYNTAX  Counter64
	MAX-ACCESS  read-only
	STATUS  current
	DESCRIPTION
		"Number of handshakes on SSLv2"
	::= { nsSslStatsGroup 215 }

sslTotSSLv3Handshakes  OBJECT-TYPE
	SYNTAX  Counter64
	MAX-ACCESS  read-only
	STATUS  current
	DESCRIPTION
		"Number of handshakes on SSLv3"
	::= { nsSslStatsGroup 216 }

sslTotTLSv1Handshakes  OBJECT-TYPE
	SYNTAX  Counter64
	MAX-ACCESS  read-only
	STATUS  current
	DESCRIPTION
		"Number of SSL handshakes on TLSv1"
	::= { nsSslStatsGroup 217 }

sslTotSSLv2ClientAuthentications  OBJECT-TYPE
	SYNTAX  Counter64
	MAX-ACCESS  read-only
	STATUS  current
	DESCRIPTION
		"Number of client authentications done on SSLv2"
	::= { nsSslStatsGroup 218 }

sslTotSSLv3ClientAuthentications  OBJECT-TYPE
	SYNTAX  Counter64
	MAX-ACCESS  read-only
	STATUS  current
	DESCRIPTION
		"Number of client authentications done on SSLv3"
	::= { nsSslStatsGroup 219 }

sslTotTLSv1ClientAuthentications  OBJECT-TYPE
	SYNTAX  Counter64
	MAX-ACCESS  read-only
	STATUS  current
	DESCRIPTION
		"Number of client authentications done on TLSv1"
	::= { nsSslStatsGroup 220 }

sslTotRSA512keyExchanges  OBJECT-TYPE
	SYNTAX  Counter64
	MAX-ACCESS  read-only
	STATUS  current
	DESCRIPTION
		"Number of RSA 512-bit key exchanges"
	::= { nsSslStatsGroup 221 }

sslTotRSA1024keyExchanges  OBJECT-TYPE
	SYNTAX  Counter64
	MAX-ACCESS  read-only
	STATUS  current
	DESCRIPTION
		"Number of RSA 1024-bit key exchanges"
	::= { nsSslStatsGroup 222 }

sslTotRSA2048keyExchanges  OBJECT-TYPE
	SYNTAX  Counter64
	MAX-ACCESS  read-only
	STATUS  current
	DESCRIPTION
		"Number of RSA 2048-bit key exchanges"
	::= { nsSslStatsGroup 223 }

sslTotDH512keyExchanges  OBJECT-TYPE
	SYNTAX  Counter64
	MAX-ACCESS  read-only
	STATUS  current
	DESCRIPTION
		"Number of Diffie-Helman 512-bit key exchanges"
	::= { nsSslStatsGroup 224 }

sslTotDH1024keyExchanges  OBJECT-TYPE
	SYNTAX  Counter64
	MAX-ACCESS  read-only
	STATUS  current
	DESCRIPTION
		"Number of Diffie-Helman 1024-bit key exchanges"
	::= { nsSslStatsGroup 225 }

sslTotDH2048keyExchanges  OBJECT-TYPE
	SYNTAX  Counter64
	MAX-ACCESS  read-only
	STATUS  current
	DESCRIPTION
		"Number of Diffie-Helman 2048-bit key exchanges"
	::= { nsSslStatsGroup 226 }

sslTotRSAAuthorizations  OBJECT-TYPE
	SYNTAX  Counter64
	MAX-ACCESS  read-only
	STATUS  current
	DESCRIPTION
		"Number of RSA authentications"
	::= { nsSslStatsGroup 227 }

sslTotDHAuthorizations  OBJECT-TYPE
	SYNTAX  Counter64
	MAX-ACCESS  read-only
	STATUS  current
	DESCRIPTION
		"Number of Diffie-Helman authentications"
	::= { nsSslStatsGroup 228 }

sslTotDSSAuthorizations  OBJECT-TYPE
	SYNTAX  Counter64
	MAX-ACCESS  read-only
	STATUS  current
	DESCRIPTION
		" Total number of times DSS authorization used. "
	::= { nsSslStatsGroup 229 }

sslTotNULLAuthorizations  OBJECT-TYPE
	SYNTAX  Counter64
	MAX-ACCESS  read-only
	STATUS  current
	DESCRIPTION
		"Number of Null authentications"
	::= { nsSslStatsGroup 230 }

sslTot40BitRC4Ciphers  OBJECT-TYPE
	SYNTAX  Counter64
	MAX-ACCESS  read-only
	STATUS  current
	DESCRIPTION
		"Number of RC4 40-bit cipher encryptions"
	::= { nsSslStatsGroup 231 }

sslTot56BitRC4Ciphers  OBJECT-TYPE
	SYNTAX  Counter64
	MAX-ACCESS  read-only
	STATUS  current
	DESCRIPTION
		"Number of RC4 56-bit cipher encryptions"
	::= { nsSslStatsGroup 232 }

sslTot64BitRC4Ciphers  OBJECT-TYPE
	SYNTAX  Counter64
	MAX-ACCESS  read-only
	STATUS  current
	DESCRIPTION
		"Number of RC4 64-bit cipher encryptions"
	::= { nsSslStatsGroup 233 }

sslTot128BitRC4Ciphers  OBJECT-TYPE
	SYNTAX  Counter64
	MAX-ACCESS  read-only
	STATUS  current
	DESCRIPTION
		"Number of RC4 128-bit cipher encryptions"
	::= { nsSslStatsGroup 234 }

sslTot40BitDESCiphers  OBJECT-TYPE
	SYNTAX  Counter64
	MAX-ACCESS  read-only
	STATUS  current
	DESCRIPTION
		"Number of DES 40-bit cipher encryptions"
	::= { nsSslStatsGroup 235 }

sslTot56BitDESCiphers  OBJECT-TYPE
	SYNTAX  Counter64
	MAX-ACCESS  read-only
	STATUS  current
	DESCRIPTION
		"Number of DES 56-bit cipher encryptions"
	::= { nsSslStatsGroup 236 }

sslTot168Bit3DESCiphers  OBJECT-TYPE
	SYNTAX  Counter64
	MAX-ACCESS  read-only
	STATUS  current
	DESCRIPTION
		"Number of DES 168-bit cipher encryptions"
	::= { nsSslStatsGroup 237 }

sslTot40BitRC2Ciphers  OBJECT-TYPE
	SYNTAX  Counter64
	MAX-ACCESS  read-only
	STATUS  current
	DESCRIPTION
		"Number of RC2 40-bit cipher encryptions"
	::= { nsSslStatsGroup 238 }

sslTot56BitRC2Ciphers  OBJECT-TYPE
	SYNTAX  Counter64
	MAX-ACCESS  read-only
	STATUS  current
	DESCRIPTION
		"Number of RC2 56-bit cipher encryptions"
	::= { nsSslStatsGroup 239 }

sslTot128BitRC2Ciphers  OBJECT-TYPE
	SYNTAX  Counter64
	MAX-ACCESS  read-only
	STATUS  current
	DESCRIPTION
		"Number of RC2 128-bit cipher encryptions"
	::= { nsSslStatsGroup 240 }

sslTot128BitIDEACiphers  OBJECT-TYPE
	SYNTAX  Counter64
	MAX-ACCESS  read-only
	STATUS  current
	DESCRIPTION
		"Number of IDEA 128-bit cipher encryptions"
	::= { nsSslStatsGroup 241 }

sslTotNULLCiphers  OBJECT-TYPE
	SYNTAX  Counter64
	MAX-ACCESS  read-only
	STATUS  current
	DESCRIPTION
		"Number of Null cipher encryptions"
	::= { nsSslStatsGroup 242 }

sslTotMD5Mac  OBJECT-TYPE
	SYNTAX  Counter64
	MAX-ACCESS  read-only
	STATUS  current
	DESCRIPTION
		"Number of MD5 hashes"
	::= { nsSslStatsGroup 243 }

sslTotSHAMac  OBJECT-TYPE
	SYNTAX  Counter64
	MAX-ACCESS  read-only
	STATUS  current
	DESCRIPTION
		"Number of SHA hashes"
	::= { nsSslStatsGroup 244 }

sslTotOffloadBulkDES  OBJECT-TYPE
	SYNTAX  Counter64
	MAX-ACCESS  read-only
	STATUS  current
	DESCRIPTION
		"Number of DES encryptions offloaded to crypto card"
	::= { nsSslStatsGroup 245 }

sslTotOffloadRSAKeyExchanges  OBJECT-TYPE
	SYNTAX  Counter64
	MAX-ACCESS  read-only
	STATUS  current
	DESCRIPTION
		"Number of RSA key exchanges offloaded to crypto card"
	::= { nsSslStatsGroup 246 }

sslTotOffloadDHKeyExchanges  OBJECT-TYPE
	SYNTAX  Counter64
	MAX-ACCESS  read-only
	STATUS  current
	DESCRIPTION
		"Number of DH key exchanges offloaded to crypto card"
	::= { nsSslStatsGroup 247 }

sslTotOffloadSignRSA  OBJECT-TYPE
	SYNTAX  Counter64
	MAX-ACCESS  read-only
	STATUS  current
	DESCRIPTION
		"Number of RSA sign operations offloaded to crypto card"
	::= { nsSslStatsGroup 248 }

sslBeTotSessions  OBJECT-TYPE
	SYNTAX  Counter64
	MAX-ACCESS  read-only
	STATUS  current
	DESCRIPTION
		"Number of Backend SSL sessions"
	::= { nsSslStatsGroup 260 }

sslBeTotSSLv3Sessions  OBJECT-TYPE
	SYNTAX  Counter64
	MAX-ACCESS  read-only
	STATUS  current
	DESCRIPTION
		"Number of Backend SSLv3 sessions"
	::= { nsSslStatsGroup 261 }

sslBeTotTLSv1Sessions  OBJECT-TYPE
	SYNTAX  Counter64
	MAX-ACCESS  read-only
	STATUS  current
	DESCRIPTION
		"Number of Backend TLSv1 sessions"
	::= { nsSslStatsGroup 262 }

sslBeExpiredSessions  OBJECT-TYPE
	SYNTAX  Counter64
	MAX-ACCESS  read-only
	STATUS  current
	DESCRIPTION
		"Number of Backend export sessions"
	::= { nsSslStatsGroup 263 }

sslBeTotSessionMultiplexAttempts  OBJECT-TYPE
	SYNTAX  Counter64
	MAX-ACCESS  read-only
	STATUS  current
	DESCRIPTION
		"Number of Backend SSL session multiplex attempts"
	::= { nsSslStatsGroup 264 }

sslBeTotSessionMultiplexAttemptSuccess  OBJECT-TYPE
	SYNTAX  Counter64
	MAX-ACCESS  read-only
	STATUS  current
	DESCRIPTION
		"Number of Backend SSL session multiplex successes"
	::= { nsSslStatsGroup 265 }

sslBeTotSessionMultiplexAttemptFails  OBJECT-TYPE
	SYNTAX  Counter64
	MAX-ACCESS  read-only
	STATUS  current
	DESCRIPTION
		"Number of Backend SSL session multiplex failures"
	::= { nsSslStatsGroup 266 }

sslBeMaxMultiplexedSessions  OBJECT-TYPE
	SYNTAX  Counter64
	MAX-ACCESS  read-only
	STATUS  current
	DESCRIPTION
		"Number of Backend SSL sessions reused"
	::= { nsSslStatsGroup 267 }

sslBeTotSSLv3Handshakes  OBJECT-TYPE
	SYNTAX  Counter64
	MAX-ACCESS  read-only
	STATUS  current
	DESCRIPTION
		"Number of Backend SSLv3 handshakes"
	::= { nsSslStatsGroup 268 }

sslBeTotTLSv1Handshakes  OBJECT-TYPE
	SYNTAX  Counter64
	MAX-ACCESS  read-only
	STATUS  current
	DESCRIPTION
		"Number of Backend TLSv1 handshakes"
	::= { nsSslStatsGroup 269 }

sslBeTotSSLv3ClientAuthentications  OBJECT-TYPE
	SYNTAX  Counter64
	MAX-ACCESS  read-only
	STATUS  current
	DESCRIPTION
		"Number of Backend SSLv3 client authentications"
	::= { nsSslStatsGroup 270 }

sslBeTotTLSv1ClientAuthentications  OBJECT-TYPE
	SYNTAX  Counter64
	MAX-ACCESS  read-only
	STATUS  current
	DESCRIPTION
		"Number of Backend TLSv1 client authentications"
	::= { nsSslStatsGroup 271 }

sslBeTotRSA512keyExchanges  OBJECT-TYPE
	SYNTAX  Counter64
	MAX-ACCESS  read-only
	STATUS  current
	DESCRIPTION
		"Number of Backend RSA 512-bit key exchanges"
	::= { nsSslStatsGroup 272 }

sslBeTotRSA1024keyExchanges  OBJECT-TYPE
	SYNTAX  Counter64
	MAX-ACCESS  read-only
	STATUS  current
	DESCRIPTION
		"Number of Backend RSA 1024-bit key exchanges"
	::= { nsSslStatsGroup 273 }

sslBeTotRSA2048keyExchanges  OBJECT-TYPE
	SYNTAX  Counter64
	MAX-ACCESS  read-only
	STATUS  current
	DESCRIPTION
		"Number of Backend RSA 2048-bit key exchanges"
	::= { nsSslStatsGroup 274 }

sslBeTotDH512keyExchanges  OBJECT-TYPE
	SYNTAX  Counter64
	MAX-ACCESS  read-only
	STATUS  current
	DESCRIPTION
		"Number of Backend DH 512-bit key exchanges"
	::= { nsSslStatsGroup 275 }

sslBeTotDH1024keyExchanges  OBJECT-TYPE
	SYNTAX  Counter64
	MAX-ACCESS  read-only
	STATUS  current
	DESCRIPTION
		"Number of Backend DH 1024-bit key exchanges"
	::= { nsSslStatsGroup 276 }

sslBeTotDH2048keyExchanges  OBJECT-TYPE
	SYNTAX  Counter64
	MAX-ACCESS  read-only
	STATUS  current
	DESCRIPTION
		"Number of Backend DH 2048-bit key exchanges"
	::= { nsSslStatsGroup 277 }

sslBeTotRSAAuthorizations  OBJECT-TYPE
	SYNTAX  Counter64
	MAX-ACCESS  read-only
	STATUS  current
	DESCRIPTION
		"Number of Backend RSA authentications"
	::= { nsSslStatsGroup 278 }

sslBeTotDHAuthorizations  OBJECT-TYPE
	SYNTAX  Counter64
	MAX-ACCESS  read-only
	STATUS  current
	DESCRIPTION
		"Number of Backend DH authentications"
	::= { nsSslStatsGroup 279 }

sslBeTotDSSAuthorizations  OBJECT-TYPE
	SYNTAX  Counter64
	MAX-ACCESS  read-only
	STATUS  current
	DESCRIPTION
		"Number of Backend DSS authentications"
	::= { nsSslStatsGroup 280 }

sslBeTotNULLAuthorizations  OBJECT-TYPE
	SYNTAX  Counter64
	MAX-ACCESS  read-only
	STATUS  current
	DESCRIPTION
		"Number of Backend null authentications"
	::= { nsSslStatsGroup 281 }

sslBeTot40BitRC4Ciphers  OBJECT-TYPE
	SYNTAX  Counter64
	MAX-ACCESS  read-only
	STATUS  current
	DESCRIPTION
		"Number of Backend RC4 40-bit cipher encryptions"
	::= { nsSslStatsGroup 282 }

sslBeTot56BitRC4Ciphers  OBJECT-TYPE
	SYNTAX  Counter64
	MAX-ACCESS  read-only
	STATUS  current
	DESCRIPTION
		"Number of Backend RC4 56-bit cipher encryptions"
	::= { nsSslStatsGroup 283 }

sslBeTot64BitRC4Ciphers  OBJECT-TYPE
	SYNTAX  Counter64
	MAX-ACCESS  read-only
	STATUS  current
	DESCRIPTION
		"Number of Backend RC4 64-bit cipher encryptions"
	::= { nsSslStatsGroup 284 }

sslBeTot128BitRC4Ciphers  OBJECT-TYPE
	SYNTAX  Counter64
	MAX-ACCESS  read-only
	STATUS  current
	DESCRIPTION
		"Number of Backend RC4 128-bit cipher encryptions"
	::= { nsSslStatsGroup 285 }

sslBeTot40BitDESCiphers  OBJECT-TYPE
	SYNTAX  Counter64
	MAX-ACCESS  read-only
	STATUS  current
	DESCRIPTION
		"Number of Backend DES 40-bit cipher encryptions"
	::= { nsSslStatsGroup 286 }

sslBeTot56BitDESCiphers  OBJECT-TYPE
	SYNTAX  Counter64
	MAX-ACCESS  read-only
	STATUS  current
	DESCRIPTION
		"Number of Backend DES 56-bit cipher encryptions"
	::= { nsSslStatsGroup 287 }

sslBeTot168Bit3DESCiphers  OBJECT-TYPE
	SYNTAX  Counter64
	MAX-ACCESS  read-only
	STATUS  current
	DESCRIPTION
		"Number of Backend 3DES 168-bit cipher encryptions"
	::= { nsSslStatsGroup 288 }

sslBeTot40BitRC2Ciphers  OBJECT-TYPE
	SYNTAX  Counter64
	MAX-ACCESS  read-only
	STATUS  current
	DESCRIPTION
		"Number of Backend RC2 40-bit cipher encryptions"
	::= { nsSslStatsGroup 289 }

sslBeTot56BitRC2Ciphers  OBJECT-TYPE
	SYNTAX  Counter64
	MAX-ACCESS  read-only
	STATUS  current
	DESCRIPTION
		"Number of Backend RC2 56-bit cipher encryptions"
	::= { nsSslStatsGroup 290 }

sslBeTot128BitRC2Ciphers  OBJECT-TYPE
	SYNTAX  Counter64
	MAX-ACCESS  read-only
	STATUS  current
	DESCRIPTION
		"Number of Backend RC2 128-bit cipher encryptions"
	::= { nsSslStatsGroup 291 }

sslBeTot128BitIDEACiphers  OBJECT-TYPE
	SYNTAX  Counter64
	MAX-ACCESS  read-only
	STATUS  current
	DESCRIPTION
		"Number of Backend IDEA 128-bit cipher encryptions"
	::= { nsSslStatsGroup 292 }

sslBeTotNULLCiphers  OBJECT-TYPE
	SYNTAX  Counter64
	MAX-ACCESS  read-only
	STATUS  current
	DESCRIPTION
		"Number of Backend null cipher encryptions"
	::= { nsSslStatsGroup 293 }

sslBeTotMD5Mac  OBJECT-TYPE
	SYNTAX  Counter64
	MAX-ACCESS  read-only
	STATUS  current
	DESCRIPTION
		"Number of Backend MD5 hashes"
	::= { nsSslStatsGroup 294 }

sslBeTotSHAMac  OBJECT-TYPE
	SYNTAX  Counter64
	MAX-ACCESS  read-only
	STATUS  current
	DESCRIPTION
		"Number of Backend SHA hashes"
	::= { nsSslStatsGroup 295 }

sslCurSessions  OBJECT-TYPE
	SYNTAX  Counter32
	MAX-ACCESS  read-only
	STATUS  current
	DESCRIPTION
		"Number of active SSL sessions"
	::= { nsSslStatsGroup 296 }

sslTotOffloadBulkAES  OBJECT-TYPE
	SYNTAX  Counter64
	MAX-ACCESS  read-only
	STATUS  current
	DESCRIPTION
		"Number of AES encryptions offloaded to crypto card"
	::= { nsSslStatsGroup 297 }

sslTotOffloadBulkRC4  OBJECT-TYPE
	SYNTAX  Counter64
	MAX-ACCESS  read-only
	STATUS  current
	DESCRIPTION
		"Number of RC4 encryptions offloaded to crypto card"
	::= { nsSslStatsGroup 298 }

sslNumCardsUP  OBJECT-TYPE
	SYNTAX  Gauge32
	MAX-ACCESS  read-only
	STATUS  current
	DESCRIPTION
		"Number of ssl cards UP. If number of cards UP is lower than a threshold, a failover will be initiated."
	::= { nsSslStatsGroup 299 }

sslCards  OBJECT-TYPE
	SYNTAX  Integer32
	MAX-ACCESS  read-only
	STATUS  current
	DESCRIPTION
		"Number of SSL crypto cards present in the system"
	::= { nsSslStatsGroup 300 }

sslTotBkendSessionReNegotiate  OBJECT-TYPE
	SYNTAX  Counter64
	MAX-ACCESS  read-only
	STATUS  current
	DESCRIPTION
		"Number of Backend SSL session renegotiations"
	::= { nsSslStatsGroup 301 }

sslTotCipherAES128  OBJECT-TYPE
	SYNTAX  Counter64
	MAX-ACCESS  read-only
	STATUS  current
	DESCRIPTION
		"Number of AES 128-bit cipher encryptions"
	::= { nsSslStatsGroup 302 }

sslTotBkendSslV3Renego  OBJECT-TYPE
	SYNTAX  Counter64
	MAX-ACCESS  read-only
	STATUS  current
	DESCRIPTION
		"Number of Backend SSLv3 session renegotiations"
	::= { nsSslStatsGroup 303 }

sslTotBkendTlSvlRenego  OBJECT-TYPE
	SYNTAX  Counter64
	MAX-ACCESS  read-only
	STATUS  current
	DESCRIPTION
		"Number of Backend TLSv1 session renegotiations"
	::= { nsSslStatsGroup 304 }

sslTotCipherAES256  OBJECT-TYPE
	SYNTAX  Counter64
	MAX-ACCESS  read-only
	STATUS  current
	DESCRIPTION
		"Number of AES 256-bit cipher encryptions"
	::= { nsSslStatsGroup 305 }

sslTotBkendCipherAES128  OBJECT-TYPE
	SYNTAX  Counter64
	MAX-ACCESS  read-only
	STATUS  current
	DESCRIPTION
		"Backend AES 128-bit cipher encryptions"
	::= { nsSslStatsGroup 306 }

sslTotBkendCipherAES256  OBJECT-TYPE
	SYNTAX  Counter64
	MAX-ACCESS  read-only
	STATUS  current
	DESCRIPTION
		"Backend AES 256-bit cipher encryptions"
	::= { nsSslStatsGroup 307 }

sslTotHwEncBE  OBJECT-TYPE
	SYNTAX  Counter64
	MAX-ACCESS  read-only
	STATUS  current
	DESCRIPTION
		"Number of bytes encrypted in hardware on back-end"
	::= { nsSslStatsGroup 308 }

sslTotDec  OBJECT-TYPE
	SYNTAX  Counter64
	MAX-ACCESS  read-only
	STATUS  current
	DESCRIPTION
		"Number of bytes decrypted"
	::= { nsSslStatsGroup 309 }

sslTotSwEncFE  OBJECT-TYPE
	SYNTAX  Counter64
	MAX-ACCESS  read-only
	STATUS  current
	DESCRIPTION
		"Number of bytes encrypted in software on front-end"
	::= { nsSslStatsGroup 310 }

sslTotEncFE  OBJECT-TYPE
	SYNTAX  Counter64
	MAX-ACCESS  read-only
	STATUS  current
	DESCRIPTION
		"Number of bytes encrypted on front-end"
	::= { nsSslStatsGroup 311 }

sslTotEnc  OBJECT-TYPE
	SYNTAX  Counter64
	MAX-ACCESS  read-only
	STATUS  current
	DESCRIPTION
		"Number of bytes encrypted"
	::= { nsSslStatsGroup 312 }

sslTotDecHw  OBJECT-TYPE
	SYNTAX  Counter64
	MAX-ACCESS  read-only
	STATUS  current
	DESCRIPTION
		"Number of bytes decrypted in hardware"
	::= { nsSslStatsGroup 313 }

sslTotSwDecBE  OBJECT-TYPE
	SYNTAX  Counter64
	MAX-ACCESS  read-only
	STATUS  current
	DESCRIPTION
		"Number of bytes decrypted in software on back-end"
	::= { nsSslStatsGroup 314 }

sslTotHwDecFE  OBJECT-TYPE
	SYNTAX  Counter64
	MAX-ACCESS  read-only
	STATUS  current
	DESCRIPTION
		"Number of bytes decrypted in hardware on front-end"
	::= { nsSslStatsGroup 315 }

sslTotEncHw  OBJECT-TYPE
	SYNTAX  Counter64
	MAX-ACCESS  read-only
	STATUS  current
	DESCRIPTION
		"Number of bytes encrypted in hardware"
	::= { nsSslStatsGroup 316 }

sslTotDecSw  OBJECT-TYPE
	SYNTAX  Counter64
	MAX-ACCESS  read-only
	STATUS  current
	DESCRIPTION
		"Number of bytes decrypted in software"
	::= { nsSslStatsGroup 317 }

sslTotSwEncBE  OBJECT-TYPE
	SYNTAX  Counter64
	MAX-ACCESS  read-only
	STATUS  current
	DESCRIPTION
		"Number of bytes encrypted in software on back-end"
	::= { nsSslStatsGroup 318 }

sslTotEncSw  OBJECT-TYPE
	SYNTAX  Counter64
	MAX-ACCESS  read-only
	STATUS  current
	DESCRIPTION
		"Number of bytes encrypted in software"
	::= { nsSslStatsGroup 319 }

sslTotSwDecFE  OBJECT-TYPE
	SYNTAX  Counter64
	MAX-ACCESS  read-only
	STATUS  current
	DESCRIPTION
		"Number of bytes decrypted in software on front-end"
	::= { nsSslStatsGroup 320 }

sslTotEncBE  OBJECT-TYPE
	SYNTAX  Counter64
	MAX-ACCESS  read-only
	STATUS  current
	DESCRIPTION
		"Number of bytes encrypted on back-end"
	::= { nsSslStatsGroup 321 }

sslTotDecBE  OBJECT-TYPE
	SYNTAX  Counter64
	MAX-ACCESS  read-only
	STATUS  current
	DESCRIPTION
		"Number of bytes decrypted on back-end"
	::= { nsSslStatsGroup 322 }

sslTotHwDecBE  OBJECT-TYPE
	SYNTAX  Counter64
	MAX-ACCESS  read-only
	STATUS  current
	DESCRIPTION
		"Number of bytes decrypted in hardware on back-end"
	::= { nsSslStatsGroup 323 }

sslTotDecFE  OBJECT-TYPE
	SYNTAX  Counter64
	MAX-ACCESS  read-only
	STATUS  current
	DESCRIPTION
		"Number of bytes decrypted on front-end"
	::= { nsSslStatsGroup 324 }

sslTotHwEncFE  OBJECT-TYPE
	SYNTAX  Counter64
	MAX-ACCESS  read-only
	STATUS  current
	DESCRIPTION
		"Number of bytes encrypted in hardware on front-end"
	::= { nsSslStatsGroup 325 }

sslTotRSA4096keyExchanges  OBJECT-TYPE
	SYNTAX  Counter64
	MAX-ACCESS  read-only
	STATUS  current
	DESCRIPTION
		"Number of RSA 4096-bit key exchanges"
	::= { nsSslStatsGroup 326 }

nsHttpStatsGroup OBJECT IDENTIFIER
	::= { nsSysGroup 48 }

httpTotGetsLow  OBJECT-TYPE
	SYNTAX  Counter32
	MAX-ACCESS  read-only
	STATUS  obsolete
	DESCRIPTION
		"...OBSOLETE"
	::= { nsHttpStatsGroup 1 }

httpTotGetsHigh  OBJECT-TYPE
	SYNTAX  Counter32
	MAX-ACCESS  read-only
	STATUS  obsolete
	DESCRIPTION
		"...OBSOLETE"
	::= { nsHttpStatsGroup 2 }

httpTotPostsLow  OBJECT-TYPE
	SYNTAX  Counter32
	MAX-ACCESS  read-only
	STATUS  obsolete
	DESCRIPTION
		"...OBSOLETE"
	::= { nsHttpStatsGroup 3 }

httpTotPostsHigh  OBJECT-TYPE
	SYNTAX  Counter32
	MAX-ACCESS  read-only
	STATUS  obsolete
	DESCRIPTION
		"...OBSOLETE"
	::= { nsHttpStatsGroup 4 }

httpTotOthersLow  OBJECT-TYPE
	SYNTAX  Counter32
	MAX-ACCESS  read-only
	STATUS  obsolete
	DESCRIPTION
		"...OBSOLETE"
	::= { nsHttpStatsGroup 5 }

httpTotOthersHigh  OBJECT-TYPE
	SYNTAX  Counter32
	MAX-ACCESS  read-only
	STATUS  obsolete
	DESCRIPTION
		"...OBSOLETE"
	::= { nsHttpStatsGroup 6 }

httpTotRxRequestBytesLow  OBJECT-TYPE
	SYNTAX  Counter32
	MAX-ACCESS  read-only
	STATUS  obsolete
	DESCRIPTION
		"...OBSOLETE"
	::= { nsHttpStatsGroup 7 }

httpTotRxRequestBytesHigh  OBJECT-TYPE
	SYNTAX  Counter32
	MAX-ACCESS  read-only
	STATUS  obsolete
	DESCRIPTION
		"...OBSOLETE"
	::= { nsHttpStatsGroup 8 }

httpTotRxResponseBytesLow  OBJECT-TYPE
	SYNTAX  Counter32
	MAX-ACCESS  read-only
	STATUS  obsolete
	DESCRIPTION
		"...OBSOLETE"
	::= { nsHttpStatsGroup 9 }

httpTotRxResponseBytesHigh  OBJECT-TYPE
	SYNTAX  Counter32
	MAX-ACCESS  read-only
	STATUS  obsolete
	DESCRIPTION
		"...OBSOLETE"
	::= { nsHttpStatsGroup 10 }

httpTotTxRequestBytesLow  OBJECT-TYPE
	SYNTAX  Counter32
	MAX-ACCESS  read-only
	STATUS  obsolete
	DESCRIPTION
		"...OBSOLETE"
	::= { nsHttpStatsGroup 11 }

httpTotTxRequestBytesHigh  OBJECT-TYPE
	SYNTAX  Counter32
	MAX-ACCESS  read-only
	STATUS  obsolete
	DESCRIPTION
		"...OBSOLETE"
	::= { nsHttpStatsGroup 12 }

httpTotTxResponseBytesLow  OBJECT-TYPE
	SYNTAX  Counter32
	MAX-ACCESS  read-only
	STATUS  obsolete
	DESCRIPTION
		"...OBSOLETE"
	::= { nsHttpStatsGroup 13 }

httpTotTxResponseBytesHigh  OBJECT-TYPE
	SYNTAX  Counter32
	MAX-ACCESS  read-only
	STATUS  obsolete
	DESCRIPTION
		"...OBSOLETE"
	::= { nsHttpStatsGroup 14 }

httpTotHTTP10reqLow  OBJECT-TYPE
	SYNTAX  Counter32
	MAX-ACCESS  read-only
	STATUS  obsolete
	DESCRIPTION
		"...OBSOLETE"
	::= { nsHttpStatsGroup 15 }

httpTotHTTP10reqHigh  OBJECT-TYPE
	SYNTAX  Counter32
	MAX-ACCESS  read-only
	STATUS  obsolete
	DESCRIPTION
		"...OBSOLETE"
	::= { nsHttpStatsGroup 16 }

httpTotResponsesLow  OBJECT-TYPE
	SYNTAX  Counter32
	MAX-ACCESS  read-only
	STATUS  obsolete
	DESCRIPTION
		"...OBSOLETE"
	::= { nsHttpStatsGroup 17 }

httpTotResponsesHigh  OBJECT-TYPE
	SYNTAX  Counter32
	MAX-ACCESS  read-only
	STATUS  obsolete
	DESCRIPTION
		"...OBSOLETE"
	::= { nsHttpStatsGroup 18 }

httpTot10ResponsesLow  OBJECT-TYPE
	SYNTAX  Counter32
	MAX-ACCESS  read-only
	STATUS  obsolete
	DESCRIPTION
		"...OBSOLETE"
	::= { nsHttpStatsGroup 19 }

httpTot10ResponsesHigh  OBJECT-TYPE
	SYNTAX  Counter32
	MAX-ACCESS  read-only
	STATUS  obsolete
	DESCRIPTION
		"...OBSOLETE"
	::= { nsHttpStatsGroup 20 }

httpTotClenResponsesLow  OBJECT-TYPE
	SYNTAX  Counter32
	MAX-ACCESS  read-only
	STATUS  obsolete
	DESCRIPTION
		"...OBSOLETE"
	::= { nsHttpStatsGroup 21 }

httpTotClenResponsesHigh  OBJECT-TYPE
	SYNTAX  Counter32
	MAX-ACCESS  read-only
	STATUS  obsolete
	DESCRIPTION
		"...OBSOLETE"
	::= { nsHttpStatsGroup 22 }

httpTotChunkedResponsesLow  OBJECT-TYPE
	SYNTAX  Counter32
	MAX-ACCESS  read-only
	STATUS  obsolete
	DESCRIPTION
		"...OBSOLETE"
	::= { nsHttpStatsGroup 23 }

httpTotChunkedResponsesHigh  OBJECT-TYPE
	SYNTAX  Counter32
	MAX-ACCESS  read-only
	STATUS  obsolete
	DESCRIPTION
		"...OBSOLETE"
	::= { nsHttpStatsGroup 24 }

httpErrIncompleteRequestsLow  OBJECT-TYPE
	SYNTAX  Counter32
	MAX-ACCESS  read-only
	STATUS  obsolete
	DESCRIPTION
		"...OBSOLETE"
	::= { nsHttpStatsGroup 25 }

httpErrIncompleteRequestsHigh  OBJECT-TYPE
	SYNTAX  Counter32
	MAX-ACCESS  read-only
	STATUS  obsolete
	DESCRIPTION
		"...OBSOLETE"
	::= { nsHttpStatsGroup 26 }

httpErrIncompleteResponsesLow  OBJECT-TYPE
	SYNTAX  Counter32
	MAX-ACCESS  read-only
	STATUS  obsolete
	DESCRIPTION
		"...OBSOLETE"
	::= { nsHttpStatsGroup 27 }

httpErrIncompleteResponsesHigh  OBJECT-TYPE
	SYNTAX  Counter32
	MAX-ACCESS  read-only
	STATUS  obsolete
	DESCRIPTION
		"...OBSOLETE"
	::= { nsHttpStatsGroup 28 }

httpErrPipelinedRequestsLow  OBJECT-TYPE
	SYNTAX  Counter32
	MAX-ACCESS  read-only
	STATUS  obsolete
	DESCRIPTION
		"...OBSOLETE"
	::= { nsHttpStatsGroup 29 }

httpErrPipelinedRequestsHigh  OBJECT-TYPE
	SYNTAX  Counter32
	MAX-ACCESS  read-only
	STATUS  obsolete
	DESCRIPTION
		"...OBSOLETE"
	::= { nsHttpStatsGroup 30 }

httpErrIncompleteHeadersLow  OBJECT-TYPE
	SYNTAX  Counter32
	MAX-ACCESS  read-only
	STATUS  obsolete
	DESCRIPTION
		"...OBSOLETE"
	::= { nsHttpStatsGroup 31 }

httpErrIncompleteHeadersHigh  OBJECT-TYPE
	SYNTAX  Counter32
	MAX-ACCESS  read-only
	STATUS  obsolete
	DESCRIPTION
		"...OBSOLETE"
	::= { nsHttpStatsGroup 32 }

httpErrServerBusyLow  OBJECT-TYPE
	SYNTAX  Counter32
	MAX-ACCESS  read-only
	STATUS  obsolete
	DESCRIPTION
		"...OBSOLETE"
	::= { nsHttpStatsGroup 33 }

httpErrServerBusyHigh  OBJECT-TYPE
	SYNTAX  Counter32
	MAX-ACCESS  read-only
	STATUS  obsolete
	DESCRIPTION
		"...OBSOLETE"
	::= { nsHttpStatsGroup 34 }

httpTotChunkedReqLow  OBJECT-TYPE
	SYNTAX  Counter32
	MAX-ACCESS  read-only
	STATUS  obsolete
	DESCRIPTION
		"...OBSOLETE"
	::= { nsHttpStatsGroup 35 }

httpTotChunkedReqHigh  OBJECT-TYPE
	SYNTAX  Counter32
	MAX-ACCESS  read-only
	STATUS  obsolete
	DESCRIPTION
		"...OBSOLETE"
	::= { nsHttpStatsGroup 36 }

httpTotClenReqLow  OBJECT-TYPE
	SYNTAX  Counter32
	MAX-ACCESS  read-only
	STATUS  obsolete
	DESCRIPTION
		"...OBSOLETE"
	::= { nsHttpStatsGroup 37 }

httpTotClenReqHigh  OBJECT-TYPE
	SYNTAX  Counter32
	MAX-ACCESS  read-only
	STATUS  obsolete
	DESCRIPTION
		"...OBSOLETE"
	::= { nsHttpStatsGroup 38 }

httpErrLargeContentLow  OBJECT-TYPE
	SYNTAX  Counter32
	MAX-ACCESS  read-only
	STATUS  obsolete
	DESCRIPTION
		"...OBSOLETE"
	::= { nsHttpStatsGroup 39 }

httpErrLargeContentHigh  OBJECT-TYPE
	SYNTAX  Counter32
	MAX-ACCESS  read-only
	STATUS  obsolete
	DESCRIPTION
		"...OBSOLETE"
	::= { nsHttpStatsGroup 40 }

httpErrLargeCtlenLow  OBJECT-TYPE
	SYNTAX  Counter32
	MAX-ACCESS  read-only
	STATUS  obsolete
	DESCRIPTION
		"...OBSOLETE"
	::= { nsHttpStatsGroup 41 }

httpErrLargeCtlenHigh  OBJECT-TYPE
	SYNTAX  Counter32
	MAX-ACCESS  read-only
	STATUS  obsolete
	DESCRIPTION
		"...OBSOLETE"
	::= { nsHttpStatsGroup 42 }

httpErrLargeChunkLow  OBJECT-TYPE
	SYNTAX  Counter32
	MAX-ACCESS  read-only
	STATUS  obsolete
	DESCRIPTION
		"...OBSOLETE"
	::= { nsHttpStatsGroup 43 }

httpErrLargeChunkHigh  OBJECT-TYPE
	SYNTAX  Counter32
	MAX-ACCESS  read-only
	STATUS  obsolete
	DESCRIPTION
		"...OBSOLETE"
	::= { nsHttpStatsGroup 44 }

httpTotGets  OBJECT-TYPE
	SYNTAX  Counter64
	MAX-ACCESS  read-only
	STATUS  current
	DESCRIPTION
		"HTTP requests received using the GET method."
	::= { nsHttpStatsGroup 45 }

httpTotPosts  OBJECT-TYPE
	SYNTAX  Counter64
	MAX-ACCESS  read-only
	STATUS  current
	DESCRIPTION
		"HTTP requests received using the POST method."
	::= { nsHttpStatsGroup 46 }

httpTotOthers  OBJECT-TYPE
	SYNTAX  Counter64
	MAX-ACCESS  read-only
	STATUS  current
	DESCRIPTION
		"HTTP requests received using methods other than GET and POST. Some of the other well-defined HTTP methods are HEAD, PUT, DELETE, OPTIONS, and TRACE. User-defined methods are also allowed."
	::= { nsHttpStatsGroup 47 }

httpTotRxRequestBytes  OBJECT-TYPE
	SYNTAX  Counter64
	MAX-ACCESS  read-only
	STATUS  current
	DESCRIPTION
		"Bytes of HTTP data received."
	::= { nsHttpStatsGroup 48 }

httpTotRxResponseBytes  OBJECT-TYPE
	SYNTAX  Counter64
	MAX-ACCESS  read-only
	STATUS  current
	DESCRIPTION
		"Bytes received as response data."
	::= { nsHttpStatsGroup 49 }

httpTotTxRequestBytes  OBJECT-TYPE
	SYNTAX  Counter64
	MAX-ACCESS  read-only
	STATUS  current
	DESCRIPTION
		"Bytes of HTTP data transmitted."
	::= { nsHttpStatsGroup 50 }

httpTotTxResponseBytes  OBJECT-TYPE
	SYNTAX  Counter64
	MAX-ACCESS  read-only
	STATUS  current
	DESCRIPTION
		"Bytes transmitted as response data."
	::= { nsHttpStatsGroup 51 }

httpTot10Requests  OBJECT-TYPE
	SYNTAX  Counter64
	MAX-ACCESS  read-only
	STATUS  current
	DESCRIPTION
		"HTTP/1.0 requests received."
	::= { nsHttpStatsGroup 52 }

httpTotResponses  OBJECT-TYPE
	SYNTAX  Counter64
	MAX-ACCESS  read-only
	STATUS  current
	DESCRIPTION
		"HTTP responses sent including HTTP/1.0 and HTTP/1.1 responses."
	::= { nsHttpStatsGroup 53 }

httpTot10Responses  OBJECT-TYPE
	SYNTAX  Counter64
	MAX-ACCESS  read-only
	STATUS  current
	DESCRIPTION
		"HTTP/1.0 responses sent."
	::= { nsHttpStatsGroup 54 }

httpTotClenResponses  OBJECT-TYPE
	SYNTAX  Counter64
	MAX-ACCESS  read-only
	STATUS  current
	DESCRIPTION
		"HTTP responses sent in which the Content-length field of the HTTP header has been set. Content-length specifies the length of the content, in bytes, in the associated HTTP body."
	::= { nsHttpStatsGroup 55 }

httpTotChunkedResponses  OBJECT-TYPE
	SYNTAX  Counter64
	MAX-ACCESS  read-only
	STATUS  current
	DESCRIPTION
		"HTTP responses sent in which the Transfer-Encoding field of the HTTP header has been set to chunked. This setting is used when the server wants to start sending the response before knowing its total length. The server breaks the response into chunks and sends them in sequence, inserting the length of each chunk before the actual data. The message ends with a chunk of size zero."
	::= { nsHttpStatsGroup 56 }

httpErrIncompleteRequests  OBJECT-TYPE
	SYNTAX  Counter64
	MAX-ACCESS  read-only
	STATUS  current
	DESCRIPTION
		"HTTP requests received in which the header spans more than one packet."
	::= { nsHttpStatsGroup 57 }

httpErrIncompleteResponses  OBJECT-TYPE
	SYNTAX  Counter64
	MAX-ACCESS  read-only
	STATUS  current
	DESCRIPTION
		"HTTP responses received in which the header spans more than one packet."
	::= { nsHttpStatsGroup 58 }

httpErrPipelinedRequests  OBJECT-TYPE
	SYNTAX  Counter64
	MAX-ACCESS  read-only
	STATUS  obsolete
	DESCRIPTION
		"...OBSOLETE"
	::= { nsHttpStatsGroup 59 }

httpErrIncompleteHeaders  OBJECT-TYPE
	SYNTAX  Counter64
	MAX-ACCESS  read-only
	STATUS  current
	DESCRIPTION
		"HTTP requests and responses received in which the HTTP header spans more than one packet."
	::= { nsHttpStatsGroup 60 }

httpErrServerBusy  OBJECT-TYPE
	SYNTAX  Counter64
	MAX-ACCESS  read-only
	STATUS  current
	DESCRIPTION
		"Error responses received. Some of the error responses are: 
500 	Internal Server Error
501 	Not Implemented
502 	Bad Gateway
503 	Service Unavailable
504 	Gateway Timeout
505 	HTTP Version Not Supported"
	::= { nsHttpStatsGroup 61 }

httpTotChunkedRequests  OBJECT-TYPE
	SYNTAX  Counter64
	MAX-ACCESS  read-only
	STATUS  current
	DESCRIPTION
		"HTTP requests in which the Transfer-Encoding field of the HTTP header has been set to chunked."
	::= { nsHttpStatsGroup 62 }

httpTotClenRequests  OBJECT-TYPE
	SYNTAX  Counter64
	MAX-ACCESS  read-only
	STATUS  current
	DESCRIPTION
		"HTTP requests in which the Content-length field of the HTTP header has been set. Content-length specifies the length of the content, in bytes, in the associated HTTP body."
	::= { nsHttpStatsGroup 63 }

httpErrLargeContent  OBJECT-TYPE
	SYNTAX  Counter64
	MAX-ACCESS  read-only
	STATUS  current
	DESCRIPTION
		"Large or invalid requests and responses received."
	::= { nsHttpStatsGroup 64 }

httpErrLargeCtlen  OBJECT-TYPE
	SYNTAX  Counter64
	MAX-ACCESS  read-only
	STATUS  current
	DESCRIPTION
		"Large or invalid requests received in which the Content-length field of the HTTP header has been set. Content-length specifies the length of the content, in bytes, in the associated HTTP body."
	::= { nsHttpStatsGroup 65 }

httpErrLargeChunk  OBJECT-TYPE
	SYNTAX  Counter64
	MAX-ACCESS  read-only
	STATUS  current
	DESCRIPTION
		"Large or invalid requests received in which the Transfer-Encoding field of the HTTP header has been set to chunked."
	::= { nsHttpStatsGroup 66 }

httpTotRequests  OBJECT-TYPE
	SYNTAX  Counter64
	MAX-ACCESS  read-only
	STATUS  current
	DESCRIPTION
		"HTTP requests received, including HTTP/1.0 and HTTP/1.1 requests."
	::= { nsHttpStatsGroup 67 }

httpTot11Requests  OBJECT-TYPE
	SYNTAX  Counter64
	MAX-ACCESS  read-only
	STATUS  current
	DESCRIPTION
		"HTTP/1.1 requests received."
	::= { nsHttpStatsGroup 68 }

httpTot11Responses  OBJECT-TYPE
	SYNTAX  Counter64
	MAX-ACCESS  read-only
	STATUS  current
	DESCRIPTION
		"HTTP/1.1 responses sent."
	::= { nsHttpStatsGroup 69 }

httpTotNoClenChunkResponses  OBJECT-TYPE
	SYNTAX  Counter64
	MAX-ACCESS  read-only
	STATUS  current
	DESCRIPTION
		"FIN-terminated responses sent. In FIN-terminated responses, the server finishes sending the data and closes the connection."
	::= { nsHttpStatsGroup 70 }

httpErrNoreuseMultipart  OBJECT-TYPE
	SYNTAX  Counter64
	MAX-ACCESS  read-only
	STATUS  current
	DESCRIPTION
		"HTTP multi-part responses sent. In multi-part responses, one or more entities are encapsulated within the body of a single message."
	::= { nsHttpStatsGroup 71 }

nsCacheStatsGroup OBJECT IDENTIFIER
	::= { nsSysGroup 49 }

cacheMaxMemoryKB  OBJECT-TYPE
	SYNTAX  Counter32
	MAX-ACCESS  read-only
	STATUS  current
	DESCRIPTION
		"Largest amount of memory the NetScaler can dedicate to caching, up to 50% of available memory. A 0 value disables caching, but the caching module continues to run. "
	::= { nsCacheStatsGroup 1 }

cacheUtilizedMemoryKB  OBJECT-TYPE
	SYNTAX  Counter32
	MAX-ACCESS  read-only
	STATUS  current
	DESCRIPTION
		"Amount of memory the integrated cache is currently using."
	::= { nsCacheStatsGroup 2 }

cacheNumCached  OBJECT-TYPE
	SYNTAX  Counter32
	MAX-ACCESS  read-only
	STATUS  current
	DESCRIPTION
		"Responses currently in integrated cache. Includes responses fully downloaded, in the process of being downloaded, and expired or flushed but not yet removed."
	::= { nsCacheStatsGroup 3 }

cacheErrMemAllocLow  OBJECT-TYPE
	SYNTAX  Counter32
	MAX-ACCESS  read-only
	STATUS  obsolete
	DESCRIPTION
		"...OBSOLETE"
	::= { nsCacheStatsGroup 4 }

cacheErrMemAllocHigh  OBJECT-TYPE
	SYNTAX  Counter32
	MAX-ACCESS  read-only
	STATUS  obsolete
	DESCRIPTION
		"...OBSOLETE"
	::= { nsCacheStatsGroup 5 }

cacheTotRequestsLow  OBJECT-TYPE
	SYNTAX  Counter32
	MAX-ACCESS  read-only
	STATUS  obsolete
	DESCRIPTION
		"...OBSOLETE"
	::= { nsCacheStatsGroup 6 }

cacheTotRequestsHigh  OBJECT-TYPE
	SYNTAX  Counter32
	MAX-ACCESS  read-only
	STATUS  obsolete
	DESCRIPTION
		"...OBSOLETE"
	::= { nsCacheStatsGroup 7 }

cacheTotHitsLow  OBJECT-TYPE
	SYNTAX  Counter32
	MAX-ACCESS  read-only
	STATUS  obsolete
	DESCRIPTION
		"...OBSOLETE"
	::= { nsCacheStatsGroup 8 }

cacheTotHitsHigh  OBJECT-TYPE
	SYNTAX  Counter32
	MAX-ACCESS  read-only
	STATUS  obsolete
	DESCRIPTION
		"...OBSOLETE"
	::= { nsCacheStatsGroup 9 }

cacheTotMissesLow  OBJECT-TYPE
	SYNTAX  Counter32
	MAX-ACCESS  read-only
	STATUS  obsolete
	DESCRIPTION
		"...OBSOLETE"
	::= { nsCacheStatsGroup 10 }

cacheTotMissesHigh  OBJECT-TYPE
	SYNTAX  Counter32
	MAX-ACCESS  read-only
	STATUS  obsolete
	DESCRIPTION
		"...OBSOLETE"
	::= { nsCacheStatsGroup 11 }

cachePercentHit  OBJECT-TYPE
	SYNTAX  Counter32
	MAX-ACCESS  read-only
	STATUS  current
	DESCRIPTION
		"Cache hits as percentage of the total number of requests"
	::= { nsCacheStatsGroup 12 }

cacheRecentPercentHit  OBJECT-TYPE
	SYNTAX  Counter32
	MAX-ACCESS  read-only
	STATUS  current
	DESCRIPTION
		"Recently recorded cache hit ratio expressed as percentage"
	::= { nsCacheStatsGroup 13 }

cacheCurHits  OBJECT-TYPE
	SYNTAX  Gauge32
	MAX-ACCESS  read-only
	STATUS  current
	DESCRIPTION
		"This number should be close to the number of hits being served currently."
	::= { nsCacheStatsGroup 14 }

cacheCurMisses  OBJECT-TYPE
	SYNTAX  Gauge32
	MAX-ACCESS  read-only
	STATUS  current
	DESCRIPTION
		"Responses fetched from the origin and served from the cache. Should approximate storable misses. Does not include non-storable misses."
	::= { nsCacheStatsGroup 15 }

cacheTot304HitsLow  OBJECT-TYPE
	SYNTAX  Counter32
	MAX-ACCESS  read-only
	STATUS  obsolete
	DESCRIPTION
		"...OBSOLETE"
	::= { nsCacheStatsGroup 16 }

cacheTot304HitsHigh  OBJECT-TYPE
	SYNTAX  Counter32
	MAX-ACCESS  read-only
	STATUS  obsolete
	DESCRIPTION
		"...OBSOLETE"
	::= { nsCacheStatsGroup 17 }

cacheTotNon304HitsLow  OBJECT-TYPE
	SYNTAX  Counter32
	MAX-ACCESS  read-only
	STATUS  obsolete
	DESCRIPTION
		"...OBSOLETE"
	::= { nsCacheStatsGroup 18 }

cacheTotNon304HitsHigh  OBJECT-TYPE
	SYNTAX  Counter32
	MAX-ACCESS  read-only
	STATUS  obsolete
	DESCRIPTION
		"...OBSOLETE"
	::= { nsCacheStatsGroup 19 }

cachePercent304Hits  OBJECT-TYPE
	SYNTAX  Counter32
	MAX-ACCESS  read-only
	STATUS  current
	DESCRIPTION
		"304 responses as a percentage of all responses that the NetScaler served."
	::= { nsCacheStatsGroup 20 }

cacheRecentPercent304Hits  OBJECT-TYPE
	SYNTAX  Counter32
	MAX-ACCESS  read-only
	STATUS  current
	DESCRIPTION
		"Recently recorded ratio of 304 hits to all hits expressed as percentage"
	::= { nsCacheStatsGroup 21 }

cacheTotStoreAbleMissesLow  OBJECT-TYPE
	SYNTAX  Counter32
	MAX-ACCESS  read-only
	STATUS  obsolete
	DESCRIPTION
		"...OBSOLETE"
	::= { nsCacheStatsGroup 22 }

cacheTotStoreAbleMissesHigh  OBJECT-TYPE
	SYNTAX  Counter32
	MAX-ACCESS  read-only
	STATUS  obsolete
	DESCRIPTION
		"...OBSOLETE"
	::= { nsCacheStatsGroup 23 }

cacheTotNonStoreAbleMissesLow  OBJECT-TYPE
	SYNTAX  Counter32
	MAX-ACCESS  read-only
	STATUS  obsolete
	DESCRIPTION
		"...OBSOLETE"
	::= { nsCacheStatsGroup 24 }

cacheTotNonStoreAbleMissesHigh  OBJECT-TYPE
	SYNTAX  Counter32
	MAX-ACCESS  read-only
	STATUS  obsolete
	DESCRIPTION
		"...OBSOLETE"
	::= { nsCacheStatsGroup 25 }

cachePercentStoreAbleMiss  OBJECT-TYPE
	SYNTAX  Counter32
	MAX-ACCESS  read-only
	STATUS  current
	DESCRIPTION
		"Responses that were fetched from the origin, stored in the cache, and then served to the client, as a percentage of all cache misses."
	::= { nsCacheStatsGroup 26 }

cacheRecentPercentStoreAbleMiss  OBJECT-TYPE
	SYNTAX  Counter32
	MAX-ACCESS  read-only
	STATUS  current
	DESCRIPTION
		"Recently recorded ratio of store-able misses to all misses expressed as percentage."
	::= { nsCacheStatsGroup 27 }

cacheTotRevalidationMissLow  OBJECT-TYPE
	SYNTAX  Counter32
	MAX-ACCESS  read-only
	STATUS  obsolete
	DESCRIPTION
		"...OBSOLETE"
	::= { nsCacheStatsGroup 28 }

cacheTotRevalidationMissHigh  OBJECT-TYPE
	SYNTAX  Counter32
	MAX-ACCESS  read-only
	STATUS  obsolete
	DESCRIPTION
		"...OBSOLETE"
	::= { nsCacheStatsGroup 29 }

cacheTotFullToConditionalRequestLow  OBJECT-TYPE
	SYNTAX  Counter32
	MAX-ACCESS  read-only
	STATUS  obsolete
	DESCRIPTION
		"...OBSOLETE"
	::= { nsCacheStatsGroup 30 }

cacheTotFullToConditionalRequestHigh  OBJECT-TYPE
	SYNTAX  Counter32
	MAX-ACCESS  read-only
	STATUS  obsolete
	DESCRIPTION
		"...OBSOLETE"
	::= { nsCacheStatsGroup 31 }

cacheTotSuccessfulRevalidationLow  OBJECT-TYPE
	SYNTAX  Counter32
	MAX-ACCESS  read-only
	STATUS  obsolete
	DESCRIPTION
		"...OBSOLETE"
	::= { nsCacheStatsGroup 32 }

cacheTotSuccessfulRevalidationHigh  OBJECT-TYPE
	SYNTAX  Counter32
	MAX-ACCESS  read-only
	STATUS  obsolete
	DESCRIPTION
		"...OBSOLETE"
	::= { nsCacheStatsGroup 33 }

cachePercentSuccessfulRevalidation  OBJECT-TYPE
	SYNTAX  Counter32
	MAX-ACCESS  read-only
	STATUS  current
	DESCRIPTION
		"Percentage of times stored content was successfully revalidated by a 304 (Object Not Modifed) response rather than by a full response"
	::= { nsCacheStatsGroup 34 }

cacheRecentPercentSuccessfulRevalidation  OBJECT-TYPE
	SYNTAX  Counter32
	MAX-ACCESS  read-only
	STATUS  current
	DESCRIPTION
		"Recently recorded percentage of times stored content was successfully revalidated by a 304 response rather than by a full response"
	::= { nsCacheStatsGroup 35 }

cacheBytesServedLow  OBJECT-TYPE
	SYNTAX  Counter32
	MAX-ACCESS  read-only
	STATUS  obsolete
	DESCRIPTION
		"...OBSOLETE"
	::= { nsCacheStatsGroup 36 }

cacheBytesServedHigh  OBJECT-TYPE
	SYNTAX  Counter32
	MAX-ACCESS  read-only
	STATUS  obsolete
	DESCRIPTION
		"...OBSOLETE"
	::= { nsCacheStatsGroup 37 }

cacheCompressedBytesServedLow  OBJECT-TYPE
	SYNTAX  Counter32
	MAX-ACCESS  read-only
	STATUS  obsolete
	DESCRIPTION
		"...OBSOLETE"
	::= { nsCacheStatsGroup 38 }

cacheCompressedBytesServedHigh  OBJECT-TYPE
	SYNTAX  Counter32
	MAX-ACCESS  read-only
	STATUS  obsolete
	DESCRIPTION
		"...OBSOLETE"
	::= { nsCacheStatsGroup 39 }

cachePercentByteHit  OBJECT-TYPE
	SYNTAX  Counter32
	MAX-ACCESS  read-only
	STATUS  current
	DESCRIPTION
		"Bytes served from the cache divided by total bytes served to the client. If compression is On in the NetScaler, this ratio may not reflect the bytes served by the compression module. If the compression is Off, this ratio is the same as cachePercentOriginBandwidthSaved."
	::= { nsCacheStatsGroup 40 }

cacheRecentPercentByteHit  OBJECT-TYPE
	SYNTAX  Counter32
	MAX-ACCESS  read-only
	STATUS  current
	DESCRIPTION
		"Recently recorded cache byte hit ratio expressed as percentage. Here we define byte hit ratio as ((number of bytes served from the cache)/(total number of bytes served to the client)). This is the standard definition of Byte Hit Ratio. If compression is turned ON in NS then this ratio doesn't mean much. This might under or over estimate the origin-to-cache bandwidth saving (depending upon whether bytes served by CMP in NetScaler are more or less than compressed bytes served from the cache). If CMP is turned OFF in NS then this ratio is same as cacheRecentPercentOriginBandwidthSaved."
	::= { nsCacheStatsGroup 41 }

cachePercentOriginBandwidthSaved  OBJECT-TYPE
	SYNTAX  Counter32
	MAX-ACCESS  read-only
	STATUS  current
	DESCRIPTION
		"Percentage of origin bandwidth saved, expressed as number of bytes served from the integrated cache divided by all bytes served. The assumption is that all compression is done in the NetScaler."
	::= { nsCacheStatsGroup 42 }

cacheRecentPercentOriginBandwidthSaved  OBJECT-TYPE
	SYNTAX  Counter32
	MAX-ACCESS  read-only
	STATUS  current
	DESCRIPTION
		"Bytes served from cache divided by total bytes served to client. This ratio can be greater than 1 because of the assumption that all compression has been done in the NetScaler."
	::= { nsCacheStatsGroup 43 }

cacheErrMemAlloc  OBJECT-TYPE
	SYNTAX  Counter64
	MAX-ACCESS  read-only
	STATUS  current
	DESCRIPTION
		"Total number of times the cache failed to allocate memory to store responses."
	::= { nsCacheStatsGroup 44 }

cacheTotRequests  OBJECT-TYPE
	SYNTAX  Counter64
	MAX-ACCESS  read-only
	STATUS  current
	DESCRIPTION
		"Total cache hits plus total cache misses."
	::= { nsCacheStatsGroup 45 }

cacheTotHits  OBJECT-TYPE
	SYNTAX  Counter64
	MAX-ACCESS  read-only
	STATUS  current
	DESCRIPTION
		"Responses served from the integrated cache. These responses match a policy with a CACHE action."
	::= { nsCacheStatsGroup 46 }

cacheTotMisses  OBJECT-TYPE
	SYNTAX  Counter64
	MAX-ACCESS  read-only
	STATUS  current
	DESCRIPTION
		"Intercepted HTTP requests requiring fetches from origin server."
	::= { nsCacheStatsGroup 47 }

cacheTot304Hits  OBJECT-TYPE
	SYNTAX  Counter64
	MAX-ACCESS  read-only
	STATUS  current
	DESCRIPTION
		"Object not modified responses served from the cache. (Status code 304 served instead of the full response.)"
	::= { nsCacheStatsGroup 48 }

cacheTotNon304Hits  OBJECT-TYPE
	SYNTAX  Counter64
	MAX-ACCESS  read-only
	STATUS  current
	DESCRIPTION
		"Total number of full (non-304) responses served from the cache. A 304 status code indicates that a response has not been modified since the last time it was served"
	::= { nsCacheStatsGroup 49 }

cacheTotStoreAbleMisses  OBJECT-TYPE
	SYNTAX  Counter64
	MAX-ACCESS  read-only
	STATUS  current
	DESCRIPTION
		"Cache misses for which the fetched response is stored in the cache before serving it to the client. Storable misses conform to a built-in or user-defined caching policy that contains a CACHE action."
	::= { nsCacheStatsGroup 50 }

cacheTotNonStoreAbleMisses  OBJECT-TYPE
	SYNTAX  Counter64
	MAX-ACCESS  read-only
	STATUS  current
	DESCRIPTION
		"Cache misses for which the fetched response is not stored in the cache. These responses match policies with a NOCACHE action or are affected by Poll Every Time."
	::= { nsCacheStatsGroup 51 }

cacheTotRevalidationMiss  OBJECT-TYPE
	SYNTAX  Counter64
	MAX-ACCESS  read-only
	STATUS  current
	DESCRIPTION
		"Responses that an intervening cache revalidated with the integrated cache before serving, as determined by a Cache-Control: Max-Age header configurable in the integrated cache"
	::= { nsCacheStatsGroup 52 }

cacheTotFullToConditionalRequest  OBJECT-TYPE
	SYNTAX  Counter64
	MAX-ACCESS  read-only
	STATUS  current
	DESCRIPTION
		"Number of user-agent requests for a cached  Poll Every Time (PET) response that were sent to the origin server as conditional requests. "
	::= { nsCacheStatsGroup 53 }

cacheTotSuccessfulRevalidation  OBJECT-TYPE
	SYNTAX  Counter64
	MAX-ACCESS  read-only
	STATUS  current
	DESCRIPTION
		"Total number of times stored content was successfully revalidated by a 304 Not Modified response from the origin."
	::= { nsCacheStatsGroup 54 }

cacheTotResponseBytes  OBJECT-TYPE
	SYNTAX  Counter64
	MAX-ACCESS  read-only
	STATUS  current
	DESCRIPTION
		"Total number of HTTP response bytes served by NetScaler from both the origin and the cache"
	::= { nsCacheStatsGroup 55 }

cacheBytesServed  OBJECT-TYPE
	SYNTAX  Counter64
	MAX-ACCESS  read-only
	STATUS  current
	DESCRIPTION
		"Total number of bytes served from the integrated cache"
	::= { nsCacheStatsGroup 56 }

cacheCompressedBytesServed  OBJECT-TYPE
	SYNTAX  Counter64
	MAX-ACCESS  read-only
	STATUS  current
	DESCRIPTION
		"Number of compressed bytes served from the cache"
	::= { nsCacheStatsGroup 57 }

cacheTotPetRequests  OBJECT-TYPE
	SYNTAX  Counter64
	MAX-ACCESS  read-only
	STATUS  current
	DESCRIPTION
		"Requests that triggered a search of a content group that has Poll Every Time (PET) enabled (always consult the origin server before serving cached data)."
	::= { nsCacheStatsGroup 58 }

cacheTotPetHits  OBJECT-TYPE
	SYNTAX  Counter64
	MAX-ACCESS  read-only
	STATUS  current
	DESCRIPTION
		"Number of times a cache hit was found during a search of a content group that has Poll Every Time enabled."
	::= { nsCacheStatsGroup 59 }

cachePercentPetHits  OBJECT-TYPE
	SYNTAX  Counter32
	MAX-ACCESS  read-only
	STATUS  current
	DESCRIPTION
		"Percentage of cache hits in content groups that have Poll Every Time enabled, relative to all searches of content groups with Poll Every Time enabled. "
	::= { nsCacheStatsGroup 60 }

cacheTotParameterizedRequests  OBJECT-TYPE
	SYNTAX  Counter64
	MAX-ACCESS  read-only
	STATUS  current
	DESCRIPTION
		"Total number of requests where the content group has hit and invalidation parameters or selectors."
	::= { nsCacheStatsGroup 61 }

cacheTotParameterizedHits  OBJECT-TYPE
	SYNTAX  Counter64
	MAX-ACCESS  read-only
	STATUS  current
	DESCRIPTION
		"Parameterized requests resulting in either a 304 or non-304 hit."
	::= { nsCacheStatsGroup 62 }

cacheTotParameterizedNon304Hits  OBJECT-TYPE
	SYNTAX  Counter64
	MAX-ACCESS  read-only
	STATUS  current
	DESCRIPTION
		"Parameterized requests resulting in a full response (not status code 304: Object Not Updated) served from the cache."
	::= { nsCacheStatsGroup 63 }

cacheTotParameterized304Hits  OBJECT-TYPE
	SYNTAX  Counter64
	MAX-ACCESS  read-only
	STATUS  current
	DESCRIPTION
		"Parameterized requests resulting in an object not modified (status code 304) response. "
	::= { nsCacheStatsGroup 64 }

cachePercentParameterized304Hits  OBJECT-TYPE
	SYNTAX  Counter32
	MAX-ACCESS  read-only
	STATUS  current
	DESCRIPTION
		"Percentage of parameterized 304 hits relative to all parameterized hits."
	::= { nsCacheStatsGroup 65 }

cacheRecentPercentParameterizedHits  OBJECT-TYPE
	SYNTAX  Counter32
	MAX-ACCESS  read-only
	STATUS  current
	DESCRIPTION
		"Recently recorded ratio of parameterized 304 hits to all parameterized hits expressed as a percentage"
	::= { nsCacheStatsGroup 66 }

cacheTotInvalidationRequests  OBJECT-TYPE
	SYNTAX  Counter64
	MAX-ACCESS  read-only
	STATUS  current
	DESCRIPTION
		"Requests that match an invalidation policy and result in expiration of specific cached responses or entire content groups."
	::= { nsCacheStatsGroup 67 }

cacheTotNonParameterizedInvalidationRequests  OBJECT-TYPE
	SYNTAX  Counter64
	MAX-ACCESS  read-only
	STATUS  current
	DESCRIPTION
		"Requests that match an invalidation policy where the invalGroups parameter is configured and expires one or more content groups."
	::= { nsCacheStatsGroup 68 }

cacheTotParameterizedInvalidationRequests  OBJECT-TYPE
	SYNTAX  Counter64
	MAX-ACCESS  read-only
	STATUS  current
	DESCRIPTION
		"Requests matching a policy with an invalidation (INVAL) action and a content group that uses an invalidation selector or parameters."
	::= { nsCacheStatsGroup 69 }

cacheLargestResponseReceived  OBJECT-TYPE
	SYNTAX  Counter32
	MAX-ACCESS  read-only
	STATUS  current
	DESCRIPTION
		"Size, in bytes, of largest response sent to client from the cache or the origin server."
	::= { nsCacheStatsGroup 70 }

cacheTotFlashcacheMisses  OBJECT-TYPE
	SYNTAX  Counter64
	MAX-ACCESS  read-only
	STATUS  current
	DESCRIPTION
		"Number of requests to a content group with flash cache enabled that were cache misses. Flash cache distributes the response to all the clients in aqueue."
	::= { nsCacheStatsGroup 71 }

cacheTotFlashcacheHits  OBJECT-TYPE
	SYNTAX  Counter64
	MAX-ACCESS  read-only
	STATUS  current
	DESCRIPTION
		"Number of requests to a content group with flash cache enabled that were cache hits. The flash cache setting queues requests that arrive simultaneously and distributes the response to all the clients in the queue."
	::= { nsCacheStatsGroup 72 }

cacheTotExpireAtLastByte  OBJECT-TYPE
	SYNTAX  Counter64
	MAX-ACCESS  read-only
	STATUS  current
	DESCRIPTION
		"Instances of content expiring immediately after receiving the last body byte due to the Expire at Last Byte setting for the content group."
	::= { nsCacheStatsGroup 73 }

cacheNumMarker  OBJECT-TYPE
	SYNTAX  Counter32
	MAX-ACCESS  read-only
	STATUS  current
	DESCRIPTION
		"Marker objects created when a response exceeds the maximum or minimum size for entries in its content group or has not yet received the minimum number of hits required for items in its content group."
	::= { nsCacheStatsGroup 74 }

nsCompressionStatsGroup OBJECT IDENTIFIER
	::= { nsSysGroup 50 }

compTotalRequests  OBJECT-TYPE
	SYNTAX  Counter64
	MAX-ACCESS  read-only
	STATUS  current
	DESCRIPTION
		"Number of HTTP compression requests the NetScaler receives for which the response is successfully compressed. For example, after you enable compression and configure services, if you send requests to the NetScaler with the following header information: “Accept-Encoding: gzip, deflate”, and NetScaler compresses the corresponding response, this counter is incremented."
	::= { nsCompressionStatsGroup 1 }

compTotalTxBytes  OBJECT-TYPE
	SYNTAX  Counter64
	MAX-ACCESS  read-only
	STATUS  current
	DESCRIPTION
		"Number of bytes the NetScaler sends to the client after compressing the response from the server."
	::= { nsCompressionStatsGroup 2 }

compTotalRxBytes  OBJECT-TYPE
	SYNTAX  Counter64
	MAX-ACCESS  read-only
	STATUS  current
	DESCRIPTION
		"Number of bytes that can be compressed, which the NetScaler receives from the server. This gives the content length of the response that the NetScaler receives from server."
	::= { nsCompressionStatsGroup 3 }

compTotalTxPackets  OBJECT-TYPE
	SYNTAX  Counter64
	MAX-ACCESS  read-only
	STATUS  current
	DESCRIPTION
		"Number of HTTP packets that the NetScaler sends to the client after compressing the response from the server."
	::= { nsCompressionStatsGroup 4 }

compTotalRxPackets  OBJECT-TYPE
	SYNTAX  Counter64
	MAX-ACCESS  read-only
	STATUS  current
	DESCRIPTION
		"Number of HTTP packets that can be compressed, which the NetScaler receives from the server."
	::= { nsCompressionStatsGroup 5 }

compRatio  OBJECT-TYPE
	SYNTAX  Gauge32
	MAX-ACCESS  read-only
	STATUS  current
	DESCRIPTION
		"Ratio of compressible data received to compressed data transmitted expressed as percentage."
	::= { nsCompressionStatsGroup 6 }

compTotalDataCompressionRatio  OBJECT-TYPE
	SYNTAX  Gauge32
	MAX-ACCESS  read-only
	STATUS  current
	DESCRIPTION
		"Ratio of total HTTP data received to total HTTP data transmitted expressed as percentage."
	::= { nsCompressionStatsGroup 7 }

compTcpTotalTxBytes  OBJECT-TYPE
	SYNTAX  Counter64
	MAX-ACCESS  read-only
	STATUS  current
	DESCRIPTION
		"Number of bytes that the NetScaler sends to the client after compressing the response from the server."
	::= { nsCompressionStatsGroup 8 }

compTcpTotalRxBytes  OBJECT-TYPE
	SYNTAX  Counter64
	MAX-ACCESS  read-only
	STATUS  current
	DESCRIPTION
		"Number of bytes that can be compressed, which the NetScaler receives from the server. This gives the content length of the response that the NetScaler receives from server."
	::= { nsCompressionStatsGroup 9 }

compTcpTotalTxPackets  OBJECT-TYPE
	SYNTAX  Counter64
	MAX-ACCESS  read-only
	STATUS  current
	DESCRIPTION
		"Number of TCP packets that the NetScaler sends to the client after compressing the response from the server."
	::= { nsCompressionStatsGroup 10 }

compTcpTotalRxPackets  OBJECT-TYPE
	SYNTAX  Counter64
	MAX-ACCESS  read-only
	STATUS  current
	DESCRIPTION
		"Total number of compressible packets received by NetScaler."
	::= { nsCompressionStatsGroup 11 }

compTcpTotalQuantum  OBJECT-TYPE
	SYNTAX  Counter64
	MAX-ACCESS  read-only
	STATUS  current
	DESCRIPTION
		"Number of times the NetScaler compresses a quantum of data.  NetScaler buffers the data received from the server till it reaches the quantum size and then compresses the buffered data and transmits to the client."
	::= { nsCompressionStatsGroup 12 }

compTcpTotalPush  OBJECT-TYPE
	SYNTAX  Counter64
	MAX-ACCESS  read-only
	STATUS  current
	DESCRIPTION
		"Number of times the NetScaler compresses data on receiving a TCP PUSH flag from the server. The PUSH flag ensures that data is compressed immediately without waiting for the buffered data size to reach the quantum size."
	::= { nsCompressionStatsGroup 13 }

compTcpTotalEoi  OBJECT-TYPE
	SYNTAX  Counter64
	MAX-ACCESS  read-only
	STATUS  current
	DESCRIPTION
		"Number of times the NetScaler compresses data on receiving End Of Input (FIN packet).  When the NetScaler receives End Of Input (FIN packet), it compresses the buffered data immediately without waiting for the buffered data size to reach the quantum size."
	::= { nsCompressionStatsGroup 14 }

compTcpTotalTimer  OBJECT-TYPE
	SYNTAX  Counter64
	MAX-ACCESS  read-only
	STATUS  current
	DESCRIPTION
		"Number of times the NetScaler compresses data on expiration of data accumulation timer. The timer expires if the server response is very slow and consequently, the NetScaler does not receive response for a certain amount of time.  Under such a condition, the NetScaler compresses the buffered data immediately without waiting for the buffered data size to reach the quantum size."
	::= { nsCompressionStatsGroup 15 }

compTcpRatio  OBJECT-TYPE
	SYNTAX  Gauge32
	MAX-ACCESS  read-only
	STATUS  current
	DESCRIPTION
		"Ratio of compressible data received to compressed data transmitted expressed as percentage."
	::= { nsCompressionStatsGroup 16 }

compTcpBandwidthSaving  OBJECT-TYPE
	SYNTAX  Integer32
	MAX-ACCESS  read-only
	STATUS  current
	DESCRIPTION
		"Bandwidth saving from TCP compression expressed as percentage."
	::= { nsCompressionStatsGroup 17 }

deCompTcpRxPackets  OBJECT-TYPE
	SYNTAX  Counter64
	MAX-ACCESS  read-only
	STATUS  current
	DESCRIPTION
		"Total number of compressed packets received by NetScaler."
	::= { nsCompressionStatsGroup 18 }

deCompTcpTxPackets  OBJECT-TYPE
	SYNTAX  Counter64
	MAX-ACCESS  read-only
	STATUS  current
	DESCRIPTION
		"Total number of decompressed packets transmitted by NetScaler."
	::= { nsCompressionStatsGroup 19 }

deCompTcpRxBytes  OBJECT-TYPE
	SYNTAX  Counter64
	MAX-ACCESS  read-only
	STATUS  current
	DESCRIPTION
		"Total number of compressed bytes received by NetScaler."
	::= { nsCompressionStatsGroup 20 }

deCompTcpTxBytes  OBJECT-TYPE
	SYNTAX  Counter64
	MAX-ACCESS  read-only
	STATUS  current
	DESCRIPTION
		"Total number of decompressed bytes transmitted by NetScaler."
	::= { nsCompressionStatsGroup 21 }

deCompTcpErrData  OBJECT-TYPE
	SYNTAX  Counter64
	MAX-ACCESS  read-only
	STATUS  current
	DESCRIPTION
		"Number of data errors encountered while decompressing."
	::= { nsCompressionStatsGroup 22 }

deCompTcpErrLessData  OBJECT-TYPE
	SYNTAX  Counter64
	MAX-ACCESS  read-only
	STATUS  current
	DESCRIPTION
		"Number of times NetScaler received less data than declared by protocol."
	::= { nsCompressionStatsGroup 23 }

deCompTcpErrMoreData  OBJECT-TYPE
	SYNTAX  Counter64
	MAX-ACCESS  read-only
	STATUS  current
	DESCRIPTION
		"Number of times NetScaler received more data than declared by protocol."
	::= { nsCompressionStatsGroup 24 }

deCompTcpErrMemory  OBJECT-TYPE
	SYNTAX  Counter64
	MAX-ACCESS  read-only
	STATUS  current
	DESCRIPTION
		"Number of times memory failures occurred while decompressing."
	::= { nsCompressionStatsGroup 25 }

deCompTcpErrUnknown  OBJECT-TYPE
	SYNTAX  Counter64
	MAX-ACCESS  read-only
	STATUS  current
	DESCRIPTION
		"Number of times unknown errors occurred while decompressing."
	::= { nsCompressionStatsGroup 26 }

deCompTcpRatio  OBJECT-TYPE
	SYNTAX  Gauge32
	MAX-ACCESS  read-only
	STATUS  current
	DESCRIPTION
		"Ratio of decompressed data transmitted to compressed data received expressed as percentage."
	::= { nsCompressionStatsGroup 27 }

deCompTcpBandwidthSaving  OBJECT-TYPE
	SYNTAX  Integer32
	MAX-ACCESS  read-only
	STATUS  current
	DESCRIPTION
		"Bandwidth saving from compression expressed as percentage."
	::= { nsCompressionStatsGroup 28 }

delCompTotalRequests  OBJECT-TYPE
	SYNTAX  Counter64
	MAX-ACCESS  read-only
	STATUS  current
	DESCRIPTION
		"Total number of delta compression requests received by NetScaler."
	::= { nsCompressionStatsGroup 29 }

delCompFirstAccess  OBJECT-TYPE
	SYNTAX  Counter64
	MAX-ACCESS  read-only
	STATUS  current
	DESCRIPTION
		"Total number of delta compression first accesses."
	::= { nsCompressionStatsGroup 30 }

delCompDone  OBJECT-TYPE
	SYNTAX  Counter64
	MAX-ACCESS  read-only
	STATUS  current
	DESCRIPTION
		"Total number of delta compressions done by NetScaler."
	::= { nsCompressionStatsGroup 31 }

delCompTcpRxBytes  OBJECT-TYPE
	SYNTAX  Counter64
	MAX-ACCESS  read-only
	STATUS  current
	DESCRIPTION
		"Total number of delta-compressible bytes received by NetScaler."
	::= { nsCompressionStatsGroup 32 }

delCompTcpTxBytes  OBJECT-TYPE
	SYNTAX  Counter64
	MAX-ACCESS  read-only
	STATUS  current
	DESCRIPTION
		"Total number of delta-compressed bytes transmitted by NetScaler."
	::= { nsCompressionStatsGroup 33 }

delCompTcpRxPackets  OBJECT-TYPE
	SYNTAX  Counter64
	MAX-ACCESS  read-only
	STATUS  current
	DESCRIPTION
		"Number of delta-compressible packets received."
	::= { nsCompressionStatsGroup 34 }

delCompTcpTxPackets  OBJECT-TYPE
	SYNTAX  Counter64
	MAX-ACCESS  read-only
	STATUS  current
	DESCRIPTION
		"Total number of delta-compressed packets transmitted by NetScaler."
	::= { nsCompressionStatsGroup 35 }

delCompBaseServed  OBJECT-TYPE
	SYNTAX  Counter64
	MAX-ACCESS  read-only
	STATUS  current
	DESCRIPTION
		"Total number of basefile requests served by NetScaler."
	::= { nsCompressionStatsGroup 36 }

delCompBaseTcpTxBytes  OBJECT-TYPE
	SYNTAX  Counter64
	MAX-ACCESS  read-only
	STATUS  current
	DESCRIPTION
		"Number of basefile bytes transmitted by NetScaler."
	::= { nsCompressionStatsGroup 37 }

delCompErrBypassed  OBJECT-TYPE
	SYNTAX  Counter64
	MAX-ACCESS  read-only
	STATUS  current
	DESCRIPTION
		"Number of times delta-compression bypassed by NetScaler."
	::= { nsCompressionStatsGroup 39 }

delCompErrBFileWHdrFailed  OBJECT-TYPE
	SYNTAX  Counter64
	MAX-ACCESS  read-only
	STATUS  current
	DESCRIPTION
		"Number of times basefile could not be updated in NetScaler cache."
	::= { nsCompressionStatsGroup 40 }

delCompErrNostoreMiss  OBJECT-TYPE
	SYNTAX  Counter64
	MAX-ACCESS  read-only
	STATUS  current
	DESCRIPTION
		"Number of times basefile was not found in NetScaler cache."
	::= { nsCompressionStatsGroup 41 }

delCompErrReqinfoToobig  OBJECT-TYPE
	SYNTAX  Counter64
	MAX-ACCESS  read-only
	STATUS  current
	DESCRIPTION
		"Number of times basefile request URL was too large."
	::= { nsCompressionStatsGroup 42 }

delCompErrReqinfoAllocfail  OBJECT-TYPE
	SYNTAX  Counter64
	MAX-ACCESS  read-only
	STATUS  current
	DESCRIPTION
		"Number of times requested basefile could not be allocated."
	::= { nsCompressionStatsGroup 43 }

delCompErrSessallocFail  OBJECT-TYPE
	SYNTAX  Counter64
	MAX-ACCESS  read-only
	STATUS  current
	DESCRIPTION
		"Number of times delta compression session could not be allocated."
	::= { nsCompressionStatsGroup 44 }

delCmpRatio  OBJECT-TYPE
	SYNTAX  Gauge32
	MAX-ACCESS  read-only
	STATUS  current
	DESCRIPTION
		"Ratio of compressible data received to compressed data transmitted expressed as percentage."
	::= { nsCompressionStatsGroup 45 }

delBwSaving  OBJECT-TYPE
	SYNTAX  Integer32
	MAX-ACCESS  read-only
	STATUS  current
	DESCRIPTION
		"Bandwidth saving from delta compression expressed as percentage."
	::= { nsCompressionStatsGroup 46 }

nsGslbGroup OBJECT IDENTIFIER
	::= { nsSysGroup 51 }

gslbGlobalStats OBJECT IDENTIFIER
	::= { nsGslbGroup 1 }

customEntries  OBJECT-TYPE
	SYNTAX  Counter32
	MAX-ACCESS  read-only
	STATUS  current
	DESCRIPTION
		"This is the number of custom locations"
	::= { gslbGlobalStats 1 }

staticEntries  OBJECT-TYPE
	SYNTAX  Counter32
	MAX-ACCESS  read-only
	STATUS  current
	DESCRIPTION
		"This is the number of static locations"
	::= { gslbGlobalStats 2 }

gslbGlobalInfo OBJECT IDENTIFIER
	::= { nsGslbGroup 2 }

gslbSitesTable  OBJECT-TYPE
	SYNTAX  SEQUENCE OF GslbSitesEntry
	MAX-ACCESS  not-accessible
	STATUS  current
	DESCRIPTION
		"This table contains gslb sites information"
	::= { gslbGlobalInfo 1 }

gslbSitesEntry  OBJECT-TYPE
	SYNTAX  GslbSitesEntry
	MAX-ACCESS  not-accessible
	STATUS  current
	DESCRIPTION
		"..."
	INDEX { siteName   }
	::= { gslbSitesTable 1 }

GslbSitesEntry ::= SEQUENCE {
	siteName  OCTET STRING,
	siteIp  IpAddress,
	siteType  SiteType,
	siteMetricExchange  MetricExchange,
	siteMepStatus  MepStatus,
	sitePublicIp  IpAddress,
	siteTotalRequests  Counter64,
	siteTotalRequestBytes  Counter64,
	siteTotalResponses  Counter64,
	siteTotalResponseBytes  Counter64,
	siteCurSrvrConnections  Gauge32,
	siteCurClntConnections  Gauge32
}

siteName  OBJECT-TYPE
	SYNTAX  OCTET STRING
	MAX-ACCESS  read-only
	STATUS  current
	DESCRIPTION
		"This is the name of the gslb site"
	::= { gslbSitesEntry 1 }

siteIp  OBJECT-TYPE
	SYNTAX  IpAddress
	MAX-ACCESS  read-only
	STATUS  current
	DESCRIPTION
		"This is the private IP address of the site"
	::= { gslbSitesEntry 2 }

siteType  OBJECT-TYPE
	SYNTAX  SiteType
	MAX-ACCESS  read-only
	STATUS  current
	DESCRIPTION
		"This indicates whether the Gslb site is local or remote."
	::= { gslbSitesEntry 3 }

siteMetricExchange  OBJECT-TYPE
	SYNTAX  MetricExchange
	MAX-ACCESS  read-only
	STATUS  current
	DESCRIPTION
		"This indicates whether metric exchange is enabled or disabled at this site."
	::= { gslbSitesEntry 4 }

siteMepStatus  OBJECT-TYPE
	SYNTAX  MepStatus
	MAX-ACCESS  read-only
	STATUS  current
	DESCRIPTION
		"This indicates the status of the Metric Exchange Policy at the site. "
	::= { gslbSitesEntry 5 }

sitePublicIp  OBJECT-TYPE
	SYNTAX  IpAddress
	MAX-ACCESS  read-only
	STATUS  current
	DESCRIPTION
		"This is the public IP address of the GSLB site."
	::= { gslbSitesEntry 6 }

siteTotalRequests  OBJECT-TYPE
	SYNTAX  Counter64
	MAX-ACCESS  read-only
	STATUS  current
	DESCRIPTION
		"The total number of requests received on the Vservers represented by all GSLB services associated with this site."
	::= { gslbSitesEntry 7 }

siteTotalRequestBytes  OBJECT-TYPE
	SYNTAX  Counter64
	MAX-ACCESS  read-only
	STATUS  current
	DESCRIPTION
		"The total number of request bytes received on the Vservers represented by all GSLB services associated with this site."
	::= { gslbSitesEntry 8 }

siteTotalResponses  OBJECT-TYPE
	SYNTAX  Counter64
	MAX-ACCESS  read-only
	STATUS  current
	DESCRIPTION
		"Number of responses received on the Vservers represented by all GSLB services associated with this site."
	::= { gslbSitesEntry 9 }

siteTotalResponseBytes  OBJECT-TYPE
	SYNTAX  Counter64
	MAX-ACCESS  read-only
	STATUS  current
	DESCRIPTION
		"Number of response bytes received on the Vservers represented by all GSLB services associated with this site."
	::= { gslbSitesEntry 10 }

siteCurSrvrConnections  OBJECT-TYPE
	SYNTAX  Gauge32
	MAX-ACCESS  read-only
	STATUS  current
	DESCRIPTION
		"The number of current connections to the real servers behind the Vservers represented by all the GSLB services associated with this site."
	::= { gslbSitesEntry 11 }

siteCurClntConnections  OBJECT-TYPE
	SYNTAX  Gauge32
	MAX-ACCESS  read-only
	STATUS  current
	DESCRIPTION
		"The number of current client connections to the Vservers represented by all GSLB services associated with this site."
	::= { gslbSitesEntry 12 }

gslbPoliciesTable  OBJECT-TYPE
	SYNTAX  SEQUENCE OF GslbPoliciesEntry
	MAX-ACCESS  not-accessible
	STATUS  current
	DESCRIPTION
		"This table contains the policy information"
	::= { gslbGlobalInfo 2 }

gslbPoliciesEntry  OBJECT-TYPE
	SYNTAX  GslbPoliciesEntry
	MAX-ACCESS  not-accessible
	STATUS  current
	DESCRIPTION
		"..."
	INDEX { gslbPolicyName   }
	::= { gslbPoliciesTable 1 }

GslbPoliciesEntry ::= SEQUENCE {
	gslbPolicyName  OCTET STRING,
	totalHits  Counter32
}

gslbPolicyName  OBJECT-TYPE
	SYNTAX  OCTET STRING
	MAX-ACCESS  read-only
	STATUS  current
	DESCRIPTION
		"This is the policy name"
	::= { gslbPoliciesEntry 1 }

totalHits  OBJECT-TYPE
	SYNTAX  Counter32
	MAX-ACCESS  read-only
	STATUS  current
	DESCRIPTION
		"This is the total hits for the policy"
	::= { gslbPoliciesEntry 2 }

gslbDomainStats OBJECT IDENTIFIER
	::= { nsGslbGroup 3 }

nsDomainTable  OBJECT-TYPE
	SYNTAX  SEQUENCE OF NsDomainEntry
	MAX-ACCESS  not-accessible
	STATUS  current
	DESCRIPTION
		"This table contains information about the Hits on the Domains."
	::= { gslbDomainStats 1 }

nsDomainEntry  OBJECT-TYPE
	SYNTAX  NsDomainEntry
	MAX-ACCESS  not-accessible
	STATUS  current
	DESCRIPTION
		"..."
	INDEX { domainName   }
	::= { nsDomainTable 1 }

NsDomainEntry ::= SEQUENCE {
	domainName  OCTET STRING,
	dnsTotalQueries  Counter64
}

domainName  OBJECT-TYPE
	SYNTAX  OCTET STRING
	MAX-ACCESS  read-only
	STATUS  current
	DESCRIPTION
		"The domain name"
	::= { nsDomainEntry 1 }

dnsTotalQueries  OBJECT-TYPE
	SYNTAX  Counter64
	MAX-ACCESS  read-only
	STATUS  current
	DESCRIPTION
		"Total number of DNS queries received."
	::= { nsDomainEntry 2 }

nsPolicyEngineGroup OBJECT IDENTIFIER
	::= { nsSysGroup 52 }

nsPolicyStatsTable  OBJECT-TYPE
	SYNTAX  SEQUENCE OF NsPolicyStatsEntry
	MAX-ACCESS  not-accessible
	STATUS  current
	DESCRIPTION
		"This table contains the statistics for all policies"
	::= { nsPolicyEngineGroup 1 }

nsPolicyStatsEntry  OBJECT-TYPE
	SYNTAX  NsPolicyStatsEntry
	MAX-ACCESS  not-accessible
	STATUS  current
	DESCRIPTION
		"..."
	INDEX { pengPolicyName   }
	::= { nsPolicyStatsTable 1 }

NsPolicyStatsEntry ::= SEQUENCE {
	pengPolicyName  OCTET STRING,
	pengPolicyHits  Counter32,
	pengBytesIn  Counter32,
	pengBytesOut  Counter32
}

pengPolicyName  OBJECT-TYPE
	SYNTAX  OCTET STRING
	MAX-ACCESS  read-only
	STATUS  current
	DESCRIPTION
		"Name of the policy"
	::= { nsPolicyStatsEntry 1 }

pengPolicyHits  OBJECT-TYPE
	SYNTAX  Counter32
	MAX-ACCESS  read-only
	STATUS  current
	DESCRIPTION
		"Total policy hits count"
	::= { nsPolicyStatsEntry 2 }

pengBytesIn  OBJECT-TYPE
	SYNTAX  Counter32
	MAX-ACCESS  read-only
	STATUS  current
	DESCRIPTION
		"Input traffic of a compression policy"
	::= { nsPolicyStatsEntry 3 }

pengBytesOut  OBJECT-TYPE
	SYNTAX  Counter32
	MAX-ACCESS  read-only
	STATUS  current
	DESCRIPTION
		"Output traffic of a compression policy"
	::= { nsPolicyStatsEntry 4 }

nsDomainNameServiceGroup OBJECT IDENTIFIER
	::= { nsSysGroup 53 }

nsDnsServerStatsGroup OBJECT IDENTIFIER
	::= { nsDomainNameServiceGroup 1 }

dnsTotQueries  OBJECT-TYPE
	SYNTAX  Counter64
	MAX-ACCESS  read-only
	STATUS  current
	DESCRIPTION
		"Total number of DNS queries received."
	::= { nsDnsServerStatsGroup 1 }

dnsTotAnswers  OBJECT-TYPE
	SYNTAX  Counter64
	MAX-ACCESS  read-only
	STATUS  current
	DESCRIPTION
		"Total number of DNS responses received"
	::= { nsDnsServerStatsGroup 2 }

dnsTotArecQueries  OBJECT-TYPE
	SYNTAX  Counter64
	MAX-ACCESS  read-only
	STATUS  current
	DESCRIPTION
		"Total number of A queries received."
	::= { nsDnsServerStatsGroup 3 }

dnsTotAresponse  OBJECT-TYPE
	SYNTAX  Counter64
	MAX-ACCESS  read-only
	STATUS  current
	DESCRIPTION
		"Total number of A responses received."
	::= { nsDnsServerStatsGroup 4 }

dnsTotNSrecQueries  OBJECT-TYPE
	SYNTAX  Counter64
	MAX-ACCESS  read-only
	STATUS  current
	DESCRIPTION
		"Total number of NS queries received."
	::= { nsDnsServerStatsGroup 5 }

dnsTotNSresponse  OBJECT-TYPE
	SYNTAX  Counter64
	MAX-ACCESS  read-only
	STATUS  current
	DESCRIPTION
		"Total number of NS responses received."
	::= { nsDnsServerStatsGroup 6 }

dnsTotMXrecQueries  OBJECT-TYPE
	SYNTAX  Counter64
	MAX-ACCESS  read-only
	STATUS  current
	DESCRIPTION
		"Total number of MX queries received."
	::= { nsDnsServerStatsGroup 7 }

dnsTotMXresponse  OBJECT-TYPE
	SYNTAX  Counter64
	MAX-ACCESS  read-only
	STATUS  current
	DESCRIPTION
		"Total number of MX responses received."
	::= { nsDnsServerStatsGroup 8 }

dnsTotSOArecQueries  OBJECT-TYPE
	SYNTAX  Counter64
	MAX-ACCESS  read-only
	STATUS  current
	DESCRIPTION
		"Total number of SOA queries received."
	::= { nsDnsServerStatsGroup 9 }

dnsTotSOAresponse  OBJECT-TYPE
	SYNTAX  Counter64
	MAX-ACCESS  read-only
	STATUS  current
	DESCRIPTION
		"Total number of SOA responses received."
	::= { nsDnsServerStatsGroup 10 }

dnsTotCNAMErecQueries  OBJECT-TYPE
	SYNTAX  Counter64
	MAX-ACCESS  read-only
	STATUS  current
	DESCRIPTION
		"Total number of CNAME queries received."
	::= { nsDnsServerStatsGroup 11 }

dnsTotCNAMEresponse  OBJECT-TYPE
	SYNTAX  Counter64
	MAX-ACCESS  read-only
	STATUS  current
	DESCRIPTION
		"Total number of CNAME responses received."
	::= { nsDnsServerStatsGroup 12 }

dnsTotUnsupportedResponseClass  OBJECT-TYPE
	SYNTAX  Counter64
	MAX-ACCESS  read-only
	STATUS  current
	DESCRIPTION
		"Total number of responses for which response types were unsupported."
	::= { nsDnsServerStatsGroup 13 }

dnsTotUnsupportedResponseType  OBJECT-TYPE
	SYNTAX  Counter64
	MAX-ACCESS  read-only
	STATUS  current
	DESCRIPTION
		"Total number of responses for which response type requested was unsupported."
	::= { nsDnsServerStatsGroup 14 }

dnsTotUnsupportedQueries  OBJECT-TYPE
	SYNTAX  Counter64
	MAX-ACCESS  read-only
	STATUS  current
	DESCRIPTION
		"Total number of requests for which query type requested was unsupported."
	::= { nsDnsServerStatsGroup 15 }

dnsTotUnsupportedQueryClass  OBJECT-TYPE
	SYNTAX  Counter64
	MAX-ACCESS  read-only
	STATUS  current
	DESCRIPTION
		"Total number of queries for which query class was unsupported."
	::= { nsDnsServerStatsGroup 16 }

dnsTotInvalidQueryFormat  OBJECT-TYPE
	SYNTAX  Counter64
	MAX-ACCESS  read-only
	STATUS  current
	DESCRIPTION
		"Total number of queries whose format was invalid."
	::= { nsDnsServerStatsGroup 17 }

dnsTotNonAuthNoDatas  OBJECT-TYPE
	SYNTAX  Counter64
	MAX-ACCESS  read-only
	STATUS  current
	DESCRIPTION
		"Total number of responses for which there was a format error."
	::= { nsDnsServerStatsGroup 18 }

dnsTotMultiQuery  OBJECT-TYPE
	SYNTAX  Counter64
	MAX-ACCESS  read-only
	STATUS  current
	DESCRIPTION
		"Total number of Multi Query request received."
	::= { nsDnsServerStatsGroup 19 }

dnsTotStrayAnswer  OBJECT-TYPE
	SYNTAX  Counter64
	MAX-ACCESS  read-only
	STATUS  current
	DESCRIPTION
		"Total number of stray answers."
	::= { nsDnsServerStatsGroup 20 }

dnsTotCacheFlush  OBJECT-TYPE
	SYNTAX  Counter64
	MAX-ACCESS  read-only
	STATUS  current
	DESCRIPTION
		"Total number of times cache was flushed."
	::= { nsDnsServerStatsGroup 21 }

dnsTotCacheEntriesFlush  OBJECT-TYPE
	SYNTAX  Counter64
	MAX-ACCESS  read-only
	STATUS  current
	DESCRIPTION
		"Total number of cache entries flushed."
	::= { nsDnsServerStatsGroup 22 }

dnsTotServerQuery  OBJECT-TYPE
	SYNTAX  Counter64
	MAX-ACCESS  read-only
	STATUS  current
	DESCRIPTION
		"Total number of Server queries sent."
	::= { nsDnsServerStatsGroup 23 }

dnsTotServerResponse  OBJECT-TYPE
	SYNTAX  Counter64
	MAX-ACCESS  read-only
	STATUS  current
	DESCRIPTION
		"Total number of Server responses received."
	::= { nsDnsServerStatsGroup 24 }

dnsTotArecFailed  OBJECT-TYPE
	SYNTAX  Counter64
	MAX-ACCESS  read-only
	STATUS  current
	DESCRIPTION
		"Total number of times A record lookup failed."
	::= { nsDnsServerStatsGroup 25 }

dnsTotNSrecFailed  OBJECT-TYPE
	SYNTAX  Counter64
	MAX-ACCESS  read-only
	STATUS  current
	DESCRIPTION
		"Total number of times NS record lookup failed."
	::= { nsDnsServerStatsGroup 26 }

dnsTotMXrecFailed  OBJECT-TYPE
	SYNTAX  Counter64
	MAX-ACCESS  read-only
	STATUS  current
	DESCRIPTION
		"Total number of times MX record lookup failed."
	::= { nsDnsServerStatsGroup 27 }

dnsTotCNAMErecFailed  OBJECT-TYPE
	SYNTAX  Counter64
	MAX-ACCESS  read-only
	STATUS  current
	DESCRIPTION
		"Total number of times CNAME record lookup failed."
	::= { nsDnsServerStatsGroup 28 }

dnsTotArecUpdate  OBJECT-TYPE
	SYNTAX  Counter64
	MAX-ACCESS  read-only
	STATUS  current
	DESCRIPTION
		"Total number of A record updates."
	::= { nsDnsServerStatsGroup 29 }

dnsTotNSrecUpdate  OBJECT-TYPE
	SYNTAX  Counter64
	MAX-ACCESS  read-only
	STATUS  current
	DESCRIPTION
		"Total number of NS record updates."
	::= { nsDnsServerStatsGroup 30 }

dnsTotMXrecUpdate  OBJECT-TYPE
	SYNTAX  Counter64
	MAX-ACCESS  read-only
	STATUS  current
	DESCRIPTION
		"Total number of MX record updates."
	::= { nsDnsServerStatsGroup 31 }

dnsTotSOArecUpdate  OBJECT-TYPE
	SYNTAX  Counter64
	MAX-ACCESS  read-only
	STATUS  current
	DESCRIPTION
		"Total number of SOA record updates."
	::= { nsDnsServerStatsGroup 32 }

dnsTotCNAMErecUpdate  OBJECT-TYPE
	SYNTAX  Counter64
	MAX-ACCESS  read-only
	STATUS  current
	DESCRIPTION
		"Total number of CNAME record updates."
	::= { nsDnsServerStatsGroup 33 }

dnsTotRecUpdate  OBJECT-TYPE
	SYNTAX  Counter64
	MAX-ACCESS  read-only
	STATUS  current
	DESCRIPTION
		"Total number of record updates."
	::= { nsDnsServerStatsGroup 34 }

dnsTotMultiQueryDisableError  OBJECT-TYPE
	SYNTAX  Counter64
	MAX-ACCESS  read-only
	STATUS  current
	DESCRIPTION
		"Total number of times a multi query was disabled and received a multi query."
	::= { nsDnsServerStatsGroup 35 }

dnsCurArecord  OBJECT-TYPE
	SYNTAX  Gauge32
	MAX-ACCESS  read-only
	STATUS  current
	DESCRIPTION
		"Total number of A records."
	::= { nsDnsServerStatsGroup 36 }

dnsCurNSrecord  OBJECT-TYPE
	SYNTAX  Gauge32
	MAX-ACCESS  read-only
	STATUS  current
	DESCRIPTION
		"Total number of NS records."
	::= { nsDnsServerStatsGroup 37 }

dnsCurMXrecord  OBJECT-TYPE
	SYNTAX  Gauge32
	MAX-ACCESS  read-only
	STATUS  current
	DESCRIPTION
		"Total number of MX records."
	::= { nsDnsServerStatsGroup 38 }

dnsCurSOArecord  OBJECT-TYPE
	SYNTAX  Gauge32
	MAX-ACCESS  read-only
	STATUS  current
	DESCRIPTION
		"Total number of SOA records."
	::= { nsDnsServerStatsGroup 39 }

dnsCurCNAMErecord  OBJECT-TYPE
	SYNTAX  Gauge32
	MAX-ACCESS  read-only
	STATUS  current
	DESCRIPTION
		"Total number of CNAME records."
	::= { nsDnsServerStatsGroup 40 }

dnsCurAuthEntries  OBJECT-TYPE
	SYNTAX  Gauge32
	MAX-ACCESS  read-only
	STATUS  current
	DESCRIPTION
		"Total number of authoritative entries."
	::= { nsDnsServerStatsGroup 41 }

dnsCurNoAuthEntries  OBJECT-TYPE
	SYNTAX  Gauge32
	MAX-ACCESS  read-only
	STATUS  current
	DESCRIPTION
		"Total number of non-authoritative entries."
	::= { nsDnsServerStatsGroup 42 }

dnsTotAuthAns  OBJECT-TYPE
	SYNTAX  Counter64
	MAX-ACCESS  read-only
	STATUS  current
	DESCRIPTION
		"Number of queries which were authoritatively answered."
	::= { nsDnsServerStatsGroup 43 }

dnsTotAuthNoNames  OBJECT-TYPE
	SYNTAX  Counter64
	MAX-ACCESS  read-only
	STATUS  current
	DESCRIPTION
		"Number of queries for which no record was found."
	::= { nsDnsServerStatsGroup 44 }

dnsTotNoDataResps  OBJECT-TYPE
	SYNTAX  Counter64
	MAX-ACCESS  read-only
	STATUS  current
	DESCRIPTION
		"Number of DNS responses received without answer."
	::= { nsDnsServerStatsGroup 45 }

dnsTotResponseBadLen  OBJECT-TYPE
	SYNTAX  Counter64
	MAX-ACCESS  read-only
	STATUS  current
	DESCRIPTION
		"Number of DNS responses received with invalid resoure data length."
	::= { nsDnsServerStatsGroup 46 }

dnsTotReqRefusals  OBJECT-TYPE
	SYNTAX  Counter64
	MAX-ACCESS  read-only
	STATUS  current
	DESCRIPTION
		"Number of DNS requests refused."
	::= { nsDnsServerStatsGroup 47 }

dnsTotOtherErrors  OBJECT-TYPE
	SYNTAX  Counter64
	MAX-ACCESS  read-only
	STATUS  current
	DESCRIPTION
		"Total number of other errors. "
	::= { nsDnsServerStatsGroup 48 }

dnsTotPTRrecQueries  OBJECT-TYPE
	SYNTAX  Counter64
	MAX-ACCESS  read-only
	STATUS  current
	DESCRIPTION
		"Total number of PTR queries received."
	::= { nsDnsServerStatsGroup 49 }

dnsTotPTRresponse  OBJECT-TYPE
	SYNTAX  Counter64
	MAX-ACCESS  read-only
	STATUS  current
	DESCRIPTION
		"Total number of PTR responses received."
	::= { nsDnsServerStatsGroup 50 }

dnsTotPTRrecUpdate  OBJECT-TYPE
	SYNTAX  Counter64
	MAX-ACCESS  read-only
	STATUS  current
	DESCRIPTION
		"Total number of PTR record updates."
	::= { nsDnsServerStatsGroup 51 }

dnsTotPTRrecFailed  OBJECT-TYPE
	SYNTAX  Counter64
	MAX-ACCESS  read-only
	STATUS  current
	DESCRIPTION
		"Total number of times PTR record lookup failed."
	::= { nsDnsServerStatsGroup 52 }

dnsCurPTRrecord  OBJECT-TYPE
	SYNTAX  Gauge32
	MAX-ACCESS  read-only
	STATUS  current
	DESCRIPTION
		"Total number of PTR records."
	::= { nsDnsServerStatsGroup 53 }

dnsTotSRVrecQueries  OBJECT-TYPE
	SYNTAX  Counter64
	MAX-ACCESS  read-only
	STATUS  current
	DESCRIPTION
		"Total number of SRV queries received."
	::= { nsDnsServerStatsGroup 54 }

dnsTotSRVresponse  OBJECT-TYPE
	SYNTAX  Counter64
	MAX-ACCESS  read-only
	STATUS  current
	DESCRIPTION
		"Total number of SRV responses received."
	::= { nsDnsServerStatsGroup 55 }

dnsTotSRVrecUpdate  OBJECT-TYPE
	SYNTAX  Counter64
	MAX-ACCESS  read-only
	STATUS  current
	DESCRIPTION
		"Total number of SRV record updates."
	::= { nsDnsServerStatsGroup 56 }

dnsTotSRVrecFailed  OBJECT-TYPE
	SYNTAX  Counter64
	MAX-ACCESS  read-only
	STATUS  current
	DESCRIPTION
		"Total number of times SRV record lookup failed."
	::= { nsDnsServerStatsGroup 57 }

dnsCurSRVrecord  OBJECT-TYPE
	SYNTAX  Gauge32
	MAX-ACCESS  read-only
	STATUS  current
	DESCRIPTION
		"Total number of SRV records."
	::= { nsDnsServerStatsGroup 58 }

dnsTotAAAArecQueries  OBJECT-TYPE
	SYNTAX  Counter64
	MAX-ACCESS  read-only
	STATUS  current
	DESCRIPTION
		"Total number of AAAA queries received."
	::= { nsDnsServerStatsGroup 59 }

dnsTotAAAAresponse  OBJECT-TYPE
	SYNTAX  Counter64
	MAX-ACCESS  read-only
	STATUS  current
	DESCRIPTION
		"Total number of AAAA responses received."
	::= { nsDnsServerStatsGroup 60 }

dnsTotAAAArecUpdate  OBJECT-TYPE
	SYNTAX  Counter64
	MAX-ACCESS  read-only
	STATUS  current
	DESCRIPTION
		"Total number of AAAA record updates."
	::= { nsDnsServerStatsGroup 61 }

dnsTotAAAArecFailed  OBJECT-TYPE
	SYNTAX  Counter64
	MAX-ACCESS  read-only
	STATUS  current
	DESCRIPTION
		"Total number of times AAAA record lookup failed."
	::= { nsDnsServerStatsGroup 62 }

dnsCurAAAArecord  OBJECT-TYPE
	SYNTAX  Gauge32
	MAX-ACCESS  read-only
	STATUS  current
	DESCRIPTION
		"Total number of AAAA records."
	::= { nsDnsServerStatsGroup 63 }

dnsTotANYqueries  OBJECT-TYPE
	SYNTAX  Counter64
	MAX-ACCESS  read-only
	STATUS  current
	DESCRIPTION
		"Total number of ANY queries received."
	::= { nsDnsServerStatsGroup 64 }

dnsTotANYresponse  OBJECT-TYPE
	SYNTAX  Counter64
	MAX-ACCESS  read-only
	STATUS  current
	DESCRIPTION
		"Total number of ANY responses received."
	::= { nsDnsServerStatsGroup 65 }

dnsTotANYrecFailed  OBJECT-TYPE
	SYNTAX  Counter64
	MAX-ACCESS  read-only
	STATUS  current
	DESCRIPTION
		"Total number of times ANY query lookup failed."
	::= { nsDnsServerStatsGroup 66 }

dnsTotSOArecFailed  OBJECT-TYPE
	SYNTAX  Counter64
	MAX-ACCESS  read-only
	STATUS  current
	DESCRIPTION
		"Total number of times SOA record lookup failed."
	::= { nsDnsServerStatsGroup 67 }

nsIfStatsTable  OBJECT-TYPE
	SYNTAX  SEQUENCE OF NsIfStatsEntry
	MAX-ACCESS  not-accessible
	STATUS  current
	DESCRIPTION
		"The interface related statistics Table."
	::= { nsSysGroup 54 }

nsIfStatsEntry  OBJECT-TYPE
	SYNTAX  NsIfStatsEntry
	MAX-ACCESS  not-accessible
	STATUS  current
	DESCRIPTION
		"..."
	INDEX { ifName   }
	::= { nsIfStatsTable 1 }

NsIfStatsEntry ::= SEQUENCE {
	ifName  OCTET STRING,
	ifMedia  OCTET STRING,
	ifTotRxBytes  Counter64,
	ifRxAvgBandwidthUsage  Gauge32,
	ifTotRxPkts  Counter64,
	ifRxAvgPacketRate  Gauge32,
	ifTotTxBytes  Counter64,
	ifTxAvgBandwidthUsage  Gauge32,
	ifTotTxPkts  Counter64,
	ifTxAvgPacketRate  Gauge32,
	ifRxCRCErrors  Counter64,
	ifRxFrameErrors  Counter64,
	ifRxAlignmentErrors  Counter64,
	ifTxCollisions  Counter64,
	ifTxExcessCollisions  Counter64,
	ifTxLateCollisions  Counter64,
	ifTxMultiCollisionErrors  Counter64,
	ifTxCarrierError  Counter64,
	ifTotRxMbits  Counter64,
	ifTotTxMbits  Counter64,
	ifTotNetScalerPkts  Counter64,
	ifErrDroppedRxPkts  Counter64,
	ifErrLinkHangs  Counter32,
	ifLinkReinits  Counter32,
	ifErrDuplexMismatch  Counter32,
	ifErrCongestedPktsDrops  Counter64,
	ifErrCongestionLimitPktDrops  Counter64,
	ifErrPktRx  Counter64,
	ifErrRxFIFO  Counter64,
	ifErrRxNoBuffs  Counter64,
	ifErrTxNoNSB  Counter64,
	ifErrRxFCS  Counter64,
	ifErrPktTx  Counter64,
	ifErrTxFIFO  Counter64,
	ifErrTxHeartBeat  Counter64,
	ifErrTxOverflow  Counter64,
	ifErrTxDeferred  Counter64,
	ifErrDroppedTxPkts  Counter64,
	ifTotRxXonPause  Counter64,
	ifTotRxXoffPause  Counter64,
	ifTotXoffStateEntered  Counter64,
	ifTotXonSent  Counter64,
	ifTotXoffSent  Counter64,
	ifnicStsStalls  Counter32,
	ifnicTxStalls  Counter32,
	ifnicRxStalls  Counter32,
	ifnicErrDisables  Counter32,
	ifThroughput  Gauge32,
	ifMinThroughput  Integer32
}

ifName  OBJECT-TYPE
	SYNTAX  OCTET STRING
	MAX-ACCESS  read-only
	STATUS  current
	DESCRIPTION
		"The name of the interface."
	::= { nsIfStatsEntry 1 }

ifMedia  OBJECT-TYPE
	SYNTAX  OCTET STRING
	MAX-ACCESS  read-only
	STATUS  current
	DESCRIPTION
		"The media type of the interface."
	::= { nsIfStatsEntry 2 }

ifTotRxBytes  OBJECT-TYPE
	SYNTAX  Counter64
	MAX-ACCESS  read-only
	STATUS  current
	DESCRIPTION
		"Bytes received on the interface."
	::= { nsIfStatsEntry 3 }

ifRxAvgBandwidthUsage  OBJECT-TYPE
	SYNTAX  Gauge32
	MAX-ACCESS  read-only
	STATUS  current
	DESCRIPTION
		"The average rx bandwidth on interface in bitsps."
	::= { nsIfStatsEntry 4 }

ifTotRxPkts  OBJECT-TYPE
	SYNTAX  Counter64
	MAX-ACCESS  read-only
	STATUS  current
	DESCRIPTION
		"Packets received on the interface."
	::= { nsIfStatsEntry 5 }

ifRxAvgPacketRate  OBJECT-TYPE
	SYNTAX  Gauge32
	MAX-ACCESS  read-only
	STATUS  current
	DESCRIPTION
		"The average rate of incoming packets on the interface since the system start."
	::= { nsIfStatsEntry 6 }

ifTotTxBytes  OBJECT-TYPE
	SYNTAX  Counter64
	MAX-ACCESS  read-only
	STATUS  current
	DESCRIPTION
		"Bytes transmitted from the interface."
	::= { nsIfStatsEntry 7 }

ifTxAvgBandwidthUsage  OBJECT-TYPE
	SYNTAX  Gauge32
	MAX-ACCESS  read-only
	STATUS  current
	DESCRIPTION
		"The average tx bandwidth on interface in bitsps."
	::= { nsIfStatsEntry 8 }

ifTotTxPkts  OBJECT-TYPE
	SYNTAX  Counter64
	MAX-ACCESS  read-only
	STATUS  current
	DESCRIPTION
		"Packets transmitted from the interface."
	::= { nsIfStatsEntry 9 }

ifTxAvgPacketRate  OBJECT-TYPE
	SYNTAX  Gauge32
	MAX-ACCESS  read-only
	STATUS  current
	DESCRIPTION
		"The average rate of outgoing packets on the interface since the system start."
	::= { nsIfStatsEntry 10 }

ifRxCRCErrors  OBJECT-TYPE
	SYNTAX  Counter64
	MAX-ACCESS  read-only
	STATUS  current
	DESCRIPTION
		"Number of received packets with CRC errors (alignment or FCS)"
	::= { nsIfStatsEntry 11 }

ifRxFrameErrors  OBJECT-TYPE
	SYNTAX  Counter64
	MAX-ACCESS  read-only
	STATUS  current
	DESCRIPTION
		"Number of too long packets received on the interface."
	::= { nsIfStatsEntry 12 }

ifRxAlignmentErrors  OBJECT-TYPE
	SYNTAX  Counter64
	MAX-ACCESS  read-only
	STATUS  current
	DESCRIPTION
		"The number of alignment errors received on the interface."
	::= { nsIfStatsEntry 13 }

ifTxCollisions  OBJECT-TYPE
	SYNTAX  Counter64
	MAX-ACCESS  read-only
	STATUS  current
	DESCRIPTION
		"Number of collisions in transmission (half-duplex only)"
	::= { nsIfStatsEntry 14 }

ifTxExcessCollisions  OBJECT-TYPE
	SYNTAX  Counter64
	MAX-ACCESS  read-only
	STATUS  current
	DESCRIPTION
		"Number of excess collisions in transmission (half-duplex only)"
	::= { nsIfStatsEntry 15 }

ifTxLateCollisions  OBJECT-TYPE
	SYNTAX  Counter64
	MAX-ACCESS  read-only
	STATUS  current
	DESCRIPTION
		"Number of late collisions in transmission (half-duplex only)"
	::= { nsIfStatsEntry 16 }

ifTxMultiCollisionErrors  OBJECT-TYPE
	SYNTAX  Counter64
	MAX-ACCESS  read-only
	STATUS  current
	DESCRIPTION
		"Number of multi collision during transmission (half-duplex only)"
	::= { nsIfStatsEntry 17 }

ifTxCarrierError  OBJECT-TYPE
	SYNTAX  Counter64
	MAX-ACCESS  read-only
	STATUS  current
	DESCRIPTION
		"Number of carrier errors during transmission"
	::= { nsIfStatsEntry 18 }

ifTotRxMbits  OBJECT-TYPE
	SYNTAX  Counter64
	MAX-ACCESS  read-only
	STATUS  current
	DESCRIPTION
		"Number of megabits received by this interface"
	::= { nsIfStatsEntry 19 }

ifTotTxMbits  OBJECT-TYPE
	SYNTAX  Counter64
	MAX-ACCESS  read-only
	STATUS  current
	DESCRIPTION
		"Number of megabits transmitted by this interface"
	::= { nsIfStatsEntry 20 }

ifTotNetScalerPkts  OBJECT-TYPE
	SYNTAX  Counter64
	MAX-ACCESS  read-only
	STATUS  current
	DESCRIPTION
		"Packets (received on this interface) in which the destination MAC address is either the address of one of the NetScaler interfaces or the VMAC address configured by the user."
	::= { nsIfStatsEntry 21 }

ifErrDroppedRxPkts  OBJECT-TYPE
	SYNTAX  Counter64
	MAX-ACCESS  read-only
	STATUS  current
	DESCRIPTION
		"Packets dropped on the interface. Commonly dropped packets are multicast frames, spanning tree BPDUs, packets destined to a MAC not owned by the system when L2 mode is disabled, or packets tagged for a vlan that isn’t bound to the interface.  This counter will increment in most healthy networks at a steady rate regardless of traffic load.  If a sharp spike in dropped packets occurs, it generally indicates an issue with connected L2 switches, such as a forwarding database overflow resulting in packets being broadcast on all ports."
	::= { nsIfStatsEntry 22 }

ifErrLinkHangs  OBJECT-TYPE
	SYNTAX  Counter32
	MAX-ACCESS  read-only
	STATUS  current
	DESCRIPTION
		"Number of network interface card hangs because the NetScaler software detects an error on the transmission or reception path of the NIC."
	::= { nsIfStatsEntry 23 }

ifLinkReinits  OBJECT-TYPE
	SYNTAX  Counter32
	MAX-ACCESS  read-only
	STATUS  current
	DESCRIPTION
		"Number of times the link has been re-initialized. A re-initialization occurs when the link goes from the DOWN state to the UP state, or when an interface configuration parameter, such as speed or duplex, changes."
	::= { nsIfStatsEntry 24 }

ifErrDuplexMismatch  OBJECT-TYPE
	SYNTAX  Counter32
	MAX-ACCESS  read-only
	STATUS  current
	DESCRIPTION
		"Number of duplex mismatches detected on the interface. A mismatch will occur if the duplex mode is not identically set on both ends of the link."
	::= { nsIfStatsEntry 25 }

ifErrCongestedPktsDrops  OBJECT-TYPE
	SYNTAX  Counter64
	MAX-ACCESS  read-only
	STATUS  current
	DESCRIPTION
		"Number of output packets dropped due to congestion"
	::= { nsIfStatsEntry 26 }

ifErrCongestionLimitPktDrops  OBJECT-TYPE
	SYNTAX  Counter64
	MAX-ACCESS  read-only
	STATUS  current
	DESCRIPTION
		"Number of output packets dropped during the congestion time"
	::= { nsIfStatsEntry 27 }

ifErrPktRx  OBJECT-TYPE
	SYNTAX  Counter64
	MAX-ACCESS  read-only
	STATUS  current
	DESCRIPTION
		"Erroneous packets received on the interface. For example, a packet consisting of fewer than 64 bytes, is in an oversized frame, or has a checksum error."
	::= { nsIfStatsEntry 28 }

ifErrRxFIFO  OBJECT-TYPE
	SYNTAX  Counter64
	MAX-ACCESS  read-only
	STATUS  current
	DESCRIPTION
		"NIC receive FIFO memory overruns"
	::= { nsIfStatsEntry 29 }

ifErrRxNoBuffs  OBJECT-TYPE
	SYNTAX  Counter64
	MAX-ACCESS  read-only
	STATUS  current
	DESCRIPTION
		"Nunber of times there was no memory for Rx replacement buffers"
	::= { nsIfStatsEntry 30 }

ifErrTxNoNSB  OBJECT-TYPE
	SYNTAX  Counter64
	MAX-ACCESS  read-only
	STATUS  current
	DESCRIPTION
		"Number of times there was not enough memory for processing of the received data"
	::= { nsIfStatsEntry 31 }

ifErrRxFCS  OBJECT-TYPE
	SYNTAX  Counter64
	MAX-ACCESS  read-only
	STATUS  current
	DESCRIPTION
		"Number of packets received with Frame Check Sequence (FCS) errors"
	::= { nsIfStatsEntry 32 }

ifErrPktTx  OBJECT-TYPE
	SYNTAX  Counter64
	MAX-ACCESS  read-only
	STATUS  current
	DESCRIPTION
		"Erroneous packets transmitted on the interface. For example, a packet consisting of fewer than 64 bytes, is in an oversized frame, or is the result of a collision error."
	::= { nsIfStatsEntry 33 }

ifErrTxFIFO  OBJECT-TYPE
	SYNTAX  Counter64
	MAX-ACCESS  read-only
	STATUS  current
	DESCRIPTION
		"NIC transmission FIFO underruns"
	::= { nsIfStatsEntry 34 }

ifErrTxHeartBeat  OBJECT-TYPE
	SYNTAX  Counter64
	MAX-ACCESS  read-only
	STATUS  current
	DESCRIPTION
		"No 10Mb link heartbeats (Informational - 10Mb half-duplex only)"
	::= { nsIfStatsEntry 35 }

ifErrTxOverflow  OBJECT-TYPE
	SYNTAX  Counter64
	MAX-ACCESS  read-only
	STATUS  current
	DESCRIPTION
		"Number of times we had an overflow of the Tx ring (Informational)"
	::= { nsIfStatsEntry 36 }

ifErrTxDeferred  OBJECT-TYPE
	SYNTAX  Counter64
	MAX-ACCESS  read-only
	STATUS  current
	DESCRIPTION
		"Number of times a packet transmission was deferred (Informational - half-duplex only)"
	::= { nsIfStatsEntry 37 }

ifErrDroppedTxPkts  OBJECT-TYPE
	SYNTAX  Counter64
	MAX-ACCESS  read-only
	STATUS  current
	DESCRIPTION
		"Error-free outbound packets dropped in transmission on the interface due to a VLAN mismatch, an oversized packet, or a disabled network interface card."
	::= { nsIfStatsEntry 38 }

ifTotRxXonPause  OBJECT-TYPE
	SYNTAX  Counter64
	MAX-ACCESS  read-only
	STATUS  current
	DESCRIPTION
		"Number of XON pause frames received"
	::= { nsIfStatsEntry 39 }

ifTotRxXoffPause  OBJECT-TYPE
	SYNTAX  Counter64
	MAX-ACCESS  read-only
	STATUS  current
	DESCRIPTION
		"Number of XOFF pause frames received"
	::= { nsIfStatsEntry 40 }

ifTotXoffStateEntered  OBJECT-TYPE
	SYNTAX  Counter64
	MAX-ACCESS  read-only
	STATUS  current
	DESCRIPTION
		"Number of times the XOFF state was entered"
	::= { nsIfStatsEntry 41 }

ifTotXonSent  OBJECT-TYPE
	SYNTAX  Counter64
	MAX-ACCESS  read-only
	STATUS  current
	DESCRIPTION
		"Number of XON pause frames sent"
	::= { nsIfStatsEntry 42 }

ifTotXoffSent  OBJECT-TYPE
	SYNTAX  Counter64
	MAX-ACCESS  read-only
	STATUS  current
	DESCRIPTION
		"Number of XOFF pause frames sent"
	::= { nsIfStatsEntry 43 }

ifnicStsStalls  OBJECT-TYPE
	SYNTAX  Counter32
	MAX-ACCESS  read-only
	STATUS  current
	DESCRIPTION
		"System detected stalls in the transmission or reception of packets on the NIC. When the status is not updated within 0.8 seconds by the NIC hardware, the NIC is said to be in a status stall state."
	::= { nsIfStatsEntry 44 }

ifnicTxStalls  OBJECT-TYPE
	SYNTAX  Counter32
	MAX-ACCESS  read-only
	STATUS  current
	DESCRIPTION
		"System detected stalls in the transmission of packets on the NIC. When a packet posted for transmission has not been transmitted in 4 seconds, the NIC is said to be in a transmit stall state."
	::= { nsIfStatsEntry 45 }

ifnicRxStalls  OBJECT-TYPE
	SYNTAX  Counter32
	MAX-ACCESS  read-only
	STATUS  current
	DESCRIPTION
		"System registered stalls in the reception of packets on the network interface card. When the link is up for more than 10 minutes and packets have been transmitted, but no packets have been received for 16 seconds, the network interface card is said to be in a receive stall state.  This commonly occurs in lab environments when no packets, including spanning tree, are being received on the wire."
	::= { nsIfStatsEntry 46 }

ifnicErrDisables  OBJECT-TYPE
	SYNTAX  Counter32
	MAX-ACCESS  read-only
	STATUS  current
	DESCRIPTION
		"Number of times the interface has been disabled due to an error, such as a stall in the transmission or reception of packets. A disabled interface will not receive or transmit any packets."
	::= { nsIfStatsEntry 47 }

ifThroughput  OBJECT-TYPE
	SYNTAX  Gauge32
	MAX-ACCESS  read-only
	STATUS  current
	DESCRIPTION
		"Interface throughput in Mbps"
	::= { nsIfStatsEntry 48 }

ifMinThroughput  OBJECT-TYPE
	SYNTAX  Integer32
	MAX-ACCESS  read-only
	STATUS  current
	DESCRIPTION
		"Interface minimum throughput in Mbps"
	::= { nsIfStatsEntry 49 }

nsScPolicyGroup OBJECT IDENTIFIER
	::= { nsSysGroup 55 }

scPolicyStatistics OBJECT IDENTIFIER
	::= { nsScPolicyGroup 1 }

scPolicyUrlHits  OBJECT-TYPE
	SYNTAX  Counter64
	MAX-ACCESS  read-only
	STATUS  current
	DESCRIPTION
		"This counter gives the number of times netscaler matched an incoming request with a Configured sureconnect policy."
	::= { scPolicyStatistics 1 }

scPopUps  OBJECT-TYPE
	SYNTAX  Counter64
	MAX-ACCESS  read-only
	STATUS  current
	DESCRIPTION
		"This counter gives the number of times netscaler served the in-memory java script which throws up the pop up window."
	::= { scPolicyStatistics 2 }

scAltContUrls  OBJECT-TYPE
	SYNTAX  Counter64
	MAX-ACCESS  read-only
	STATUS  current
	DESCRIPTION
		"This gives the number of requests which are required to load the alternate content in the pop up window."
	::= { scPolicyStatistics 3 }

scSessionReqs  OBJECT-TYPE
	SYNTAX  Counter64
	MAX-ACCESS  read-only
	STATUS  current
	DESCRIPTION
		"This counter gives the number of requests which came in a SureConnect session."
	::= { scPolicyStatistics 4 }

scPostReqs  OBJECT-TYPE
	SYNTAX  Counter64
	MAX-ACCESS  read-only
	STATUS  current
	DESCRIPTION
		"This counter gives the number of times a post request triggered SureConnect."
	::= { scPolicyStatistics 5 }

scThresholdFail  OBJECT-TYPE
	SYNTAX  Counter64
	MAX-ACCESS  read-only
	STATUS  current
	DESCRIPTION
		"This counter gives the number of times netscaler did not serve the in-memory response because the thresholds conditions had failed."
	::= { scPolicyStatistics 6 }

scFaultyCookies  OBJECT-TYPE
	SYNTAX  Counter64
	MAX-ACCESS  read-only
	STATUS  current
	DESCRIPTION
		"This counter gives the number of times netscaler encountered corrupted SureConnect Cookies."
	::= { scPolicyStatistics 7 }

scUnSupBrow  OBJECT-TYPE
	SYNTAX  Counter64
	MAX-ACCESS  read-only
	STATUS  current
	DESCRIPTION
		"This counter gives the number of times requests came from unsupported browsers."
	::= { scPolicyStatistics 8 }

scResetStats  OBJECT-TYPE
	SYNTAX  Counter64
	MAX-ACCESS  read-only
	STATUS  current
	DESCRIPTION
		"This gives the number of times SureConnect statistics were reset."
	::= { scPolicyStatistics 9 }

scTotCondTriggered  OBJECT-TYPE
	SYNTAX  Counter64
	MAX-ACCESS  read-only
	STATUS  current
	DESCRIPTION
		"This counter gives the number of times the SC conditions were triggered."
	::= { scPolicyStatistics 10 }

scTotReissuedRequests  OBJECT-TYPE
	SYNTAX  Counter64
	MAX-ACCESS  read-only
	STATUS  current
	DESCRIPTION
		"This counter gives the number of SC reissued requests that Netscaler received."
	::= { scPolicyStatistics 11 }

scPolicyConfig OBJECT IDENTIFIER
	::= { nsScPolicyGroup 2 }

scPolicyConfigTable  OBJECT-TYPE
	SYNTAX  SEQUENCE OF ScPolicyConfigEntry
	MAX-ACCESS  not-accessible
	STATUS  current
	DESCRIPTION
		"The sure connect policy configuration table"
	::= { scPolicyConfig 1 }

scPolicyConfigEntry  OBJECT-TYPE
	SYNTAX  ScPolicyConfigEntry
	MAX-ACCESS  not-accessible
	STATUS  current
	DESCRIPTION
		"..."
	INDEX { scPolicyName   }
	::= { scPolicyConfigTable 1 }

ScPolicyConfigEntry ::= SEQUENCE {
	scPolicyName  OCTET STRING,
	scPolUrl  OCTET STRING,
	scDelayThreshold  Integer32,
	scMaxConnections  Integer32,
	scActionType  ActionType,
	scAlternateContentServiceName  OCTET STRING,
	scRuleName  OCTET STRING,
	scAlternateContentPath  OCTET STRING
}

scPolicyName  OBJECT-TYPE
	SYNTAX  OCTET STRING
	MAX-ACCESS  read-only
	STATUS  current
	DESCRIPTION
		"The name of Sure Connect policy."
	::= { scPolicyConfigEntry 1 }

scPolUrl  OBJECT-TYPE
	SYNTAX  OCTET STRING
	MAX-ACCESS  read-only
	STATUS  current
	DESCRIPTION
		"The URL in the IOH Policy."
	::= { scPolicyConfigEntry 2 }

scDelayThreshold  OBJECT-TYPE
	SYNTAX  Integer32
	MAX-ACCESS  read-only
	STATUS  current
	DESCRIPTION
		"The delay threshold for sc policy."
	::= { scPolicyConfigEntry 3 }

scMaxConnections  OBJECT-TYPE
	SYNTAX  Integer32
	MAX-ACCESS  read-only
	STATUS  current
	DESCRIPTION
		"The max connections for sc policy."
	::= { scPolicyConfigEntry 4 }

scActionType  OBJECT-TYPE
	SYNTAX  ActionType
	MAX-ACCESS  read-only
	STATUS  current
	DESCRIPTION
		"The type of action that NetScaler takes when initiating on-hold."
	::= { scPolicyConfigEntry 5 }

scAlternateContentServiceName  OBJECT-TYPE
	SYNTAX  OCTET STRING
	MAX-ACCESS  read-only
	STATUS  current
	DESCRIPTION
		"The alternate service name for the content."
	::= { scPolicyConfigEntry 6 }

scRuleName  OBJECT-TYPE
	SYNTAX  OCTET STRING
	MAX-ACCESS  read-only
	STATUS  current
	DESCRIPTION
		"The rule that the NetScaler matches with the incoming request."
	::= { scPolicyConfigEntry 7 }

scAlternateContentPath  OBJECT-TYPE
	SYNTAX  OCTET STRING
	MAX-ACCESS  read-only
	STATUS  current
	DESCRIPTION
		"The alternate path for the content."
	::= { scPolicyConfigEntry 8 }

nsSslConfigGroup OBJECT IDENTIFIER
	::= { nsSysGroup 56 }

sslCertKeyTable  OBJECT-TYPE
	SYNTAX  SEQUENCE OF SslCertKeyEntry
	MAX-ACCESS  not-accessible
	STATUS  current
	DESCRIPTION
		"The ssl  certificate key pair configuration information"
	::= { nsSslConfigGroup 1 }

sslCertKeyEntry  OBJECT-TYPE
	SYNTAX  SslCertKeyEntry
	MAX-ACCESS  not-accessible
	STATUS  current
	DESCRIPTION
		"..."
	INDEX { sslCertKeyName   }
	::= { sslCertKeyTable 1 }

SslCertKeyEntry ::= SEQUENCE {
	sslCertKeyName  OCTET STRING,
	sslCertPath  OCTET STRING,
	sslKeyPath  OCTET STRING,
	sslInputFormat  InputFormat,
	sslDaysToExpire  Integer32
}

sslCertKeyName  OBJECT-TYPE
	SYNTAX  OCTET STRING
	MAX-ACCESS  read-only
	STATUS  current
	DESCRIPTION
		"The certificate key pair Name."
	::= { sslCertKeyEntry 1 }

sslCertPath  OBJECT-TYPE
	SYNTAX  OCTET STRING
	MAX-ACCESS  read-only
	STATUS  current
	DESCRIPTION
		"The certificate path."
	::= { sslCertKeyEntry 2 }

sslKeyPath  OBJECT-TYPE
	SYNTAX  OCTET STRING
	MAX-ACCESS  read-only
	STATUS  current
	DESCRIPTION
		"The private key path."
	::= { sslCertKeyEntry 3 }

sslInputFormat  OBJECT-TYPE
	SYNTAX  InputFormat
	MAX-ACCESS  read-only
	STATUS  current
	DESCRIPTION
		"The input format of the certificate key pair."
	::= { sslCertKeyEntry 4 }

sslDaysToExpire  OBJECT-TYPE
	SYNTAX  Integer32
	MAX-ACCESS  read-only
	STATUS  current
	DESCRIPTION
		"Number of days remaining for the certificate to expire."
	::= { sslCertKeyEntry 5 }

sslCrlTable  OBJECT-TYPE
	SYNTAX  SEQUENCE OF SslCrlEntry
	MAX-ACCESS  not-accessible
	STATUS  current
	DESCRIPTION
		"The ssl CRL configuration information"
	::= { nsSslConfigGroup 2 }

sslCrlEntry  OBJECT-TYPE
	SYNTAX  SslCrlEntry
	MAX-ACCESS  not-accessible
	STATUS  current
	DESCRIPTION
		"..."
	INDEX { sslCrlName   }
	::= { sslCrlTable 1 }

SslCrlEntry ::= SEQUENCE {
	sslCrlName  OCTET STRING,
	sslCrlPath  OCTET STRING,
	sslCrlInputFormat  InputFormat
}

sslCrlName  OBJECT-TYPE
	SYNTAX  OCTET STRING
	MAX-ACCESS  read-only
	STATUS  current
	DESCRIPTION
		"The name of CRL."
	::= { sslCrlEntry 1 }

sslCrlPath  OBJECT-TYPE
	SYNTAX  OCTET STRING
	MAX-ACCESS  read-only
	STATUS  current
	DESCRIPTION
		"The CRL path."
	::= { sslCrlEntry 2 }

sslCrlInputFormat  OBJECT-TYPE
	SYNTAX  InputFormat
	MAX-ACCESS  read-only
	STATUS  current
	DESCRIPTION
		"The input format of CRL."
	::= { sslCrlEntry 3 }

sslCipherGroupTable  OBJECT-TYPE
	SYNTAX  SEQUENCE OF SslCipherGroupEntry
	MAX-ACCESS  not-accessible
	STATUS  current
	DESCRIPTION
		"The Cipher group configuration information"
	::= { nsSslConfigGroup 3 }

sslCipherGroupEntry  OBJECT-TYPE
	SYNTAX  SslCipherGroupEntry
	MAX-ACCESS  not-accessible
	STATUS  current
	DESCRIPTION
		"..."
	INDEX { sslCipherGroupName , sslCipherName }
	::= { sslCipherGroupTable 1 }

SslCipherGroupEntry ::= SEQUENCE {
	sslCipherGroupName  OCTET STRING,
	sslCipherName  OCTET STRING,
	sslCipherDesc  OCTET STRING
}

sslCipherGroupName  OBJECT-TYPE
	SYNTAX  OCTET STRING
	MAX-ACCESS  read-only
	STATUS  current
	DESCRIPTION
		"The Cipher group name."
	::= { sslCipherGroupEntry 1 }

sslCipherName  OBJECT-TYPE
	SYNTAX  OCTET STRING
	MAX-ACCESS  read-only
	STATUS  current
	DESCRIPTION
		"The Cipher name."
	::= { sslCipherGroupEntry 2 }

sslCipherDesc  OBJECT-TYPE
	SYNTAX  OCTET STRING
	MAX-ACCESS  read-only
	STATUS  current
	DESCRIPTION
		"The Cipher description."
	::= { sslCipherGroupEntry 3 }

nsDosPolicyGroup OBJECT IDENTIFIER
	::= { nsSysGroup 57 }

dosPolicyTable  OBJECT-TYPE
	SYNTAX  SEQUENCE OF DosPolicyEntry
	MAX-ACCESS  not-accessible
	STATUS  current
	DESCRIPTION
		"The dos policy configuration table"
	::= { nsDosPolicyGroup 1 }

dosPolicyEntry  OBJECT-TYPE
	SYNTAX  DosPolicyEntry
	MAX-ACCESS  not-accessible
	STATUS  current
	DESCRIPTION
		"..."
	INDEX { dosPolicyName   }
	::= { dosPolicyTable 1 }

DosPolicyEntry ::= SEQUENCE {
	dosPolicyName  OCTET STRING,
	thresholdValue  Integer32
}

dosPolicyName  OBJECT-TYPE
	SYNTAX  OCTET STRING
	MAX-ACCESS  read-only
	STATUS  current
	DESCRIPTION
		"Name of the policy"
	::= { dosPolicyEntry 1 }

thresholdValue  OBJECT-TYPE
	SYNTAX  Integer32
	MAX-ACCESS  read-only
	STATUS  current
	DESCRIPTION
		"Threshold surge count to detect an attack, for this DosPolicy"
	::= { dosPolicyEntry 2 }

dosPolicyStatistics OBJECT IDENTIFIER
	::= { nsDosPolicyGroup 2 }

dosTotConditionTriggered  OBJECT-TYPE
	SYNTAX  Counter64
	MAX-ACCESS  read-only
	STATUS  current
	DESCRIPTION
		"This counter gives the number of times Netscaler triggered the DOS JavaScript due to a condition match"
	::= { dosPolicyStatistics 1 }

dosTotValidCookies  OBJECT-TYPE
	SYNTAX  Counter64
	MAX-ACCESS  read-only
	STATUS  current
	DESCRIPTION
		"This counter gives the number of clients from whom Netscaler received a valid DOS cookie."
	::= { dosPolicyStatistics 2 }

dosTotDosPriorityClients  OBJECT-TYPE
	SYNTAX  Counter64
	MAX-ACCESS  read-only
	STATUS  current
	DESCRIPTION
		"This counter gives the number of valid clients that were given DOS priority."
	::= { dosPolicyStatistics 3 }

dosAvgValidClients  OBJECT-TYPE
	SYNTAX  Gauge32
	MAX-ACCESS  read-only
	STATUS  current
	DESCRIPTION
		"This counter gives the average number of DOS clients that retruned with a valid DOS cookie."
	::= { dosPolicyStatistics 4 }

dosAvgDospriClients  OBJECT-TYPE
	SYNTAX  Gauge32
	MAX-ACCESS  read-only
	STATUS  current
	DESCRIPTION
		"This counter gives the average number of clients that were given DOS priority"
	::= { dosPolicyStatistics 5 }

nsExpressionTable  OBJECT-TYPE
	SYNTAX  SEQUENCE OF NsExpressionEntry
	MAX-ACCESS  not-accessible
	STATUS  current
	DESCRIPTION
		"Expression related configuration"
	::= { nsSysGroup 58 }

nsExpressionEntry  OBJECT-TYPE
	SYNTAX  NsExpressionEntry
	MAX-ACCESS  not-accessible
	STATUS  current
	DESCRIPTION
		"..."
	INDEX { expressionName   }
	::= { nsExpressionTable 1 }

NsExpressionEntry ::= SEQUENCE {
	expressionName  OCTET STRING,
	expressionTotalHits  Counter64
}

expressionName  OBJECT-TYPE
	SYNTAX  OCTET STRING
	MAX-ACCESS  read-only
	STATUS  current
	DESCRIPTION
		"Name of the expression."
	::= { nsExpressionEntry 1 }

expressionTotalHits  OBJECT-TYPE
	SYNTAX  Counter64
	MAX-ACCESS  read-only
	STATUS  current
	DESCRIPTION
		"Total number of hits to this expression. "
	::= { nsExpressionEntry 2 }

nsPqPolicyGroup OBJECT IDENTIFIER
	::= { nsSysGroup 59 }

pqPolicyConfigTable  OBJECT-TYPE
	SYNTAX  SEQUENCE OF PqPolicyConfigEntry
	MAX-ACCESS  not-accessible
	STATUS  current
	DESCRIPTION
		"The priority queuing policy configuration table"
	::= { nsPqPolicyGroup 1 }

pqPolicyConfigEntry  OBJECT-TYPE
	SYNTAX  PqPolicyConfigEntry
	MAX-ACCESS  not-accessible
	STATUS  current
	DESCRIPTION
		"..."
	INDEX { pqName   }
	::= { pqPolicyConfigTable 1 }

PqPolicyConfigEntry ::= SEQUENCE {
	pqName  OCTET STRING,
	pqRuleName  OCTET STRING,
	pqQdepthThreshold  Integer32,
	pqPolQdepthThreshold  Integer32,
	pqPriority  Integer32,
	pqPolicyWeight  Integer32
}

pqName  OBJECT-TYPE
	SYNTAX  OCTET STRING
	MAX-ACCESS  read-only
	STATUS  current
	DESCRIPTION
		"The name of the PQ policy bound to Load Balancing vserver."
	::= { pqPolicyConfigEntry 1 }

pqRuleName  OBJECT-TYPE
	SYNTAX  OCTET STRING
	MAX-ACCESS  read-only
	STATUS  current
	DESCRIPTION
		"The Rule Name configuration for PQ policy."
	::= { pqPolicyConfigEntry 2 }

pqQdepthThreshold  OBJECT-TYPE
	SYNTAX  Integer32
	MAX-ACCESS  read-only
	STATUS  current
	DESCRIPTION
		"The vip threshold value for qdepth in PQ policy."
	::= { pqPolicyConfigEntry 3 }

pqPolQdepthThreshold  OBJECT-TYPE
	SYNTAX  Integer32
	MAX-ACCESS  read-only
	STATUS  current
	DESCRIPTION
		"The policy threshold value for qdepth in PQ policy."
	::= { pqPolicyConfigEntry 4 }

pqPriority  OBJECT-TYPE
	SYNTAX  Integer32
	MAX-ACCESS  read-only
	STATUS  current
	DESCRIPTION
		"The priority of this PQ policy."
	::= { pqPolicyConfigEntry 5 }

pqPolicyWeight  OBJECT-TYPE
	SYNTAX  Integer32
	MAX-ACCESS  read-only
	STATUS  current
	DESCRIPTION
		"The weight of this PQ policy."
	::= { pqPolicyConfigEntry 6 }

pqPolicyStatistics OBJECT IDENTIFIER
	::= { nsPqPolicyGroup 2 }

pqTotalPolicyMatches  OBJECT-TYPE
	SYNTAX  Counter64
	MAX-ACCESS  read-only
	STATUS  current
	DESCRIPTION
		"This counter gives the number of times Netscaler matched an incoming request with any PQ policy."
	::= { pqPolicyStatistics 1 }

pqTotalThresholdFailed  OBJECT-TYPE
	SYNTAX  Counter64
	MAX-ACCESS  read-only
	STATUS  current
	DESCRIPTION
		"This counter gives the number of times the priority queue threshold criteria was not met."
	::= { pqPolicyStatistics 2 }

pqPriority1Requests  OBJECT-TYPE
	SYNTAX  Counter64
	MAX-ACCESS  read-only
	STATUS  current
	DESCRIPTION
		"This counter gives the number of priority 1 requests that Netscaler received."
	::= { pqPolicyStatistics 3 }

pqPriority2Requests  OBJECT-TYPE
	SYNTAX  Counter64
	MAX-ACCESS  read-only
	STATUS  current
	DESCRIPTION
		"This counter gives the number of priority 2 requests that Netscaler received."
	::= { pqPolicyStatistics 4 }

pqPriority3Requests  OBJECT-TYPE
	SYNTAX  Counter64
	MAX-ACCESS  read-only
	STATUS  current
	DESCRIPTION
		"This counter gives the number of priority 3 requests that Netscaler received."
	::= { pqPolicyStatistics 5 }

crConfigGroup OBJECT IDENTIFIER
	::= { nsSysGroup 60 }

crPolicyMapConfigTable  OBJECT-TYPE
	SYNTAX  SEQUENCE OF CrPolicyMapConfigEntry
	MAX-ACCESS  not-accessible
	STATUS  current
	DESCRIPTION
		"The CR map configuration information "
	::= { crConfigGroup 1 }

crPolicyMapConfigEntry  OBJECT-TYPE
	SYNTAX  CrPolicyMapConfigEntry
	MAX-ACCESS  not-accessible
	STATUS  current
	DESCRIPTION
		"..."
	INDEX { crMapName   }
	::= { crPolicyMapConfigTable 1 }

CrPolicyMapConfigEntry ::= SEQUENCE {
	crMapName  OCTET STRING,
	crMapSrcName  OCTET STRING,
	crMapDstName  OCTET STRING,
	crMapSrcUrl  OCTET STRING,
	crMapDstUrl  OCTET STRING
}

crMapName  OBJECT-TYPE
	SYNTAX  OCTET STRING
	MAX-ACCESS  read-only
	STATUS  current
	DESCRIPTION
		"The name of the map policy."
	::= { crPolicyMapConfigEntry 1 }

crMapSrcName  OBJECT-TYPE
	SYNTAX  OCTET STRING
	MAX-ACCESS  read-only
	STATUS  current
	DESCRIPTION
		"The name of the source domain hosted by the map."
	::= { crPolicyMapConfigEntry 2 }

crMapDstName  OBJECT-TYPE
	SYNTAX  OCTET STRING
	MAX-ACCESS  read-only
	STATUS  current
	DESCRIPTION
		"The name of the destination domain hosted by the map."
	::= { crPolicyMapConfigEntry 3 }

crMapSrcUrl  OBJECT-TYPE
	SYNTAX  OCTET STRING
	MAX-ACCESS  read-only
	STATUS  current
	DESCRIPTION
		"The Url to be modified under the given source domain."
	::= { crPolicyMapConfigEntry 4 }

crMapDstUrl  OBJECT-TYPE
	SYNTAX  OCTET STRING
	MAX-ACCESS  read-only
	STATUS  current
	DESCRIPTION
		"The Url after mapping."
	::= { crPolicyMapConfigEntry 5 }

monitorCount  OBJECT-TYPE
	SYNTAX  Integer32
	MAX-ACCESS  read-only
	STATUS  current
	DESCRIPTION
		"Number of monitors in the system "
	::= { nsSysGroup 61 }

monitorBindCount  OBJECT-TYPE
	SYNTAX  Integer32
	MAX-ACCESS  read-only
	STATUS  current
	DESCRIPTION
		"Number of monitor bindings in the system"
	::= { nsSysGroup 62 }

htmlInjectionStatsGroup OBJECT IDENTIFIER
	::= { nsSysGroup 63 }

htmlInjectedBytes  OBJECT-TYPE
	SYNTAX  Counter64
	MAX-ACCESS  read-only
	STATUS  current
	DESCRIPTION
		"Number of Bytes Injected"
	::= { htmlInjectionStatsGroup 1 }

htmlInjectionSessions  OBJECT-TYPE
	SYNTAX  Counter64
	MAX-ACCESS  read-only
	STATUS  current
	DESCRIPTION
		"Number of HTML Injection Sessions"
	::= { htmlInjectionStatsGroup 2 }

htmlInjectionTotalSessions  OBJECT-TYPE
	SYNTAX  Counter64
	MAX-ACCESS  read-only
	STATUS  current
	DESCRIPTION
		"Number of HTML Injection Sessions"
	::= { htmlInjectionStatsGroup 3 }

htmlInjectMemAllocFailed  OBJECT-TYPE
	SYNTAX  Counter64
	MAX-ACCESS  read-only
	STATUS  current
	DESCRIPTION
		"Number of times Memory Allocation Failed"
	::= { htmlInjectionStatsGroup 4 }

htmlInitFailed  OBJECT-TYPE
	SYNTAX  Counter64
	MAX-ACCESS  read-only
	STATUS  current
	DESCRIPTION
		"Number of times Initialization Failed"
	::= { htmlInjectionStatsGroup 5 }

appFirewallGroup OBJECT IDENTIFIER
	::= { nsSysGroup 64 }

appFirewallStatistics OBJECT IDENTIFIER
	::= { appFirewallGroup 1 }

appFirewallRequests  OBJECT-TYPE
	SYNTAX  Counter64
	MAX-ACCESS  read-only
	STATUS  current
	DESCRIPTION
		"Number of requests received by the application firewall"
	::= { appFirewallStatistics 1 }

appFirewallResponses  OBJECT-TYPE
	SYNTAX  Counter64
	MAX-ACCESS  read-only
	STATUS  current
	DESCRIPTION
		"Number of responses handled by the application firewall"
	::= { appFirewallStatistics 2 }

appFirewallAborts  OBJECT-TYPE
	SYNTAX  Counter64
	MAX-ACCESS  read-only
	STATUS  current
	DESCRIPTION
		"Number of requests aborted by the application firewall"
	::= { appFirewallStatistics 3 }

appFirewallRedirects  OBJECT-TYPE
	SYNTAX  Counter64
	MAX-ACCESS  read-only
	STATUS  current
	DESCRIPTION
		"Number of requests redirected by the application firewall (HTTP 302)"
	::= { appFirewallStatistics 4 }

appFirewallViolStartURL  OBJECT-TYPE
	SYNTAX  Counter64
	MAX-ACCESS  read-only
	STATUS  current
	DESCRIPTION
		"Number of start URL violations seen by the application firewall"
	::= { appFirewallStatistics 5 }

appFirewallViolDenyURL  OBJECT-TYPE
	SYNTAX  Counter64
	MAX-ACCESS  read-only
	STATUS  current
	DESCRIPTION
		"Number of deny URL violations seen by the application firewall"
	::= { appFirewallStatistics 6 }

appFirewallViolBufferOverflow  OBJECT-TYPE
	SYNTAX  Counter64
	MAX-ACCESS  read-only
	STATUS  current
	DESCRIPTION
		"Number of buffer overflow violations seen by the application firewall"
	::= { appFirewallStatistics 7 }

appFirewallViolCookie  OBJECT-TYPE
	SYNTAX  Counter64
	MAX-ACCESS  read-only
	STATUS  current
	DESCRIPTION
		"Number of cookie violations seen by the application firewall"
	::= { appFirewallStatistics 8 }

appFirewallViolXSS  OBJECT-TYPE
	SYNTAX  Counter64
	MAX-ACCESS  read-only
	STATUS  current
	DESCRIPTION
		"Number of Cross-site scripting violations seen by the application firewall"
	::= { appFirewallStatistics 9 }

appFirewallViolSQL  OBJECT-TYPE
	SYNTAX  Counter64
	MAX-ACCESS  read-only
	STATUS  current
	DESCRIPTION
		"Number of SQL violations seen by the application firewall"
	::= { appFirewallStatistics 10 }

appFirewallViolFieldformat  OBJECT-TYPE
	SYNTAX  Counter64
	MAX-ACCESS  read-only
	STATUS  current
	DESCRIPTION
		"Number of field format violations seen by the application firewall"
	::= { appFirewallStatistics 11 }

appFirewallViolFieldConsistency  OBJECT-TYPE
	SYNTAX  Counter64
	MAX-ACCESS  read-only
	STATUS  current
	DESCRIPTION
		"Number of field consistency violations seen by the application firewall"
	::= { appFirewallStatistics 12 }

appFirewallViolCreditCard  OBJECT-TYPE
	SYNTAX  Counter64
	MAX-ACCESS  read-only
	STATUS  current
	DESCRIPTION
		"Number of credit card violations seen by the application firewall"
	::= { appFirewallStatistics 13 }

appFirewallViolSafeObject  OBJECT-TYPE
	SYNTAX  Counter64
	MAX-ACCESS  read-only
	STATUS  current
	DESCRIPTION
		"Number of safe object violations seen by the application firewall"
	::= { appFirewallStatistics 14 }

appFirewallTotalViol  OBJECT-TYPE
	SYNTAX  Counter64
	MAX-ACCESS  read-only
	STATUS  current
	DESCRIPTION
		"Number of violations seen by the application firewall"
	::= { appFirewallStatistics 15 }

appFirewallViolWellformednessViolations  OBJECT-TYPE
	SYNTAX  Counter64
	MAX-ACCESS  read-only
	STATUS  current
	DESCRIPTION
		"XML well-formedness violations"
	::= { appFirewallStatistics 16 }

appFirewallViolXdosViolations  OBJECT-TYPE
	SYNTAX  Counter64
	MAX-ACCESS  read-only
	STATUS  current
	DESCRIPTION
		"XML Denial of Service violations"
	::= { appFirewallStatistics 17 }

appFirewallViolMsgValViolations  OBJECT-TYPE
	SYNTAX  Counter64
	MAX-ACCESS  read-only
	STATUS  current
	DESCRIPTION
		"XML Message Validation violations"
	::= { appFirewallStatistics 18 }

appFirewallViolWSIViolations  OBJECT-TYPE
	SYNTAX  Counter64
	MAX-ACCESS  read-only
	STATUS  current
	DESCRIPTION
		"XML WS-I violations"
	::= { appFirewallStatistics 19 }

appFirewallViolXmlSqlViolations  OBJECT-TYPE
	SYNTAX  Counter64
	MAX-ACCESS  read-only
	STATUS  current
	DESCRIPTION
		"XML SQL Injection violations"
	::= { appFirewallStatistics 20 }

appFirewallViolXmlXssViolations  OBJECT-TYPE
	SYNTAX  Counter64
	MAX-ACCESS  read-only
	STATUS  current
	DESCRIPTION
		"XML Cross-Site Scripting violations"
	::= { appFirewallStatistics 21 }

appFirewallViolXmlAttachmentViolations  OBJECT-TYPE
	SYNTAX  Counter64
	MAX-ACCESS  read-only
	STATUS  current
	DESCRIPTION
		"XML Attachment violations"
	::= { appFirewallStatistics 22 }

nsRnatStatsGroup OBJECT IDENTIFIER
	::= { nsSysGroup 65 }

nsRnatGlobalStats OBJECT IDENTIFIER
	::= { nsRnatStatsGroup 1 }

rnatTotRxBytes  OBJECT-TYPE
	SYNTAX  Counter64
	MAX-ACCESS  read-only
	STATUS  current
	DESCRIPTION
		"Bytes received during RNAT sessions."
	::= { nsRnatGlobalStats 1 }

rnatTotTxBytes  OBJECT-TYPE
	SYNTAX  Counter64
	MAX-ACCESS  read-only
	STATUS  current
	DESCRIPTION
		"Bytes sent during RNAT sessions."
	::= { nsRnatGlobalStats 2 }

rnatTotRxPkts  OBJECT-TYPE
	SYNTAX  Counter64
	MAX-ACCESS  read-only
	STATUS  current
	DESCRIPTION
		"Packets received during RNAT sessions."
	::= { nsRnatGlobalStats 3 }

rnatTotTxPkts  OBJECT-TYPE
	SYNTAX  Counter64
	MAX-ACCESS  read-only
	STATUS  current
	DESCRIPTION
		"Packets sent during RNAT sessions."
	::= { nsRnatGlobalStats 4 }

rnatTotTxSyn  OBJECT-TYPE
	SYNTAX  Counter64
	MAX-ACCESS  read-only
	STATUS  current
	DESCRIPTION
		"Requests for connections sent during RNAT sessions."
	::= { nsRnatGlobalStats 5 }

rnatCurSessions  OBJECT-TYPE
	SYNTAX  Gauge32
	MAX-ACCESS  read-only
	STATUS  current
	DESCRIPTION
		"Currently active RNAT sessions."
	::= { nsRnatGlobalStats 6 }

nsRnatPerIPStatsTable  OBJECT-TYPE
	SYNTAX  SEQUENCE OF NsRnatPerIPStatsEntry
	MAX-ACCESS  not-accessible
	STATUS  current
	DESCRIPTION
		"This table contains statistics related to rnat for the natip"
	::= { nsRnatStatsGroup 2 }

nsRnatPerIPStatsEntry  OBJECT-TYPE
	SYNTAX  NsRnatPerIPStatsEntry
	MAX-ACCESS  not-accessible
	STATUS  current
	DESCRIPTION
		"..."
	INDEX { ipAddr   }
	::= { nsRnatPerIPStatsTable 1 }

NsRnatPerIPStatsEntry ::= SEQUENCE {
	ipRnatTotRxBytes  Counter64,
	ipRnatTotTxBytes  Counter64,
	ipRnatTotRxPkts  Counter64,
	ipRnatTotTxPkts  Counter64,
	ipRnatTotTxSyn  Counter64,
	ipRnatCurSessions  Gauge32
}

ipRnatTotRxBytes  OBJECT-TYPE
	SYNTAX  Counter64
	MAX-ACCESS  read-only
	STATUS  current
	DESCRIPTION
		"Bytes received on this IP address during RNAT sessions."
	::= { nsRnatPerIPStatsEntry 1 }

ipRnatTotTxBytes  OBJECT-TYPE
	SYNTAX  Counter64
	MAX-ACCESS  read-only
	STATUS  current
	DESCRIPTION
		"Bytes sent from this IP address during RNAT sessions."
	::= { nsRnatPerIPStatsEntry 2 }

ipRnatTotRxPkts  OBJECT-TYPE
	SYNTAX  Counter64
	MAX-ACCESS  read-only
	STATUS  current
	DESCRIPTION
		"Packets received on this IP address during RNAT sessions."
	::= { nsRnatPerIPStatsEntry 3 }

ipRnatTotTxPkts  OBJECT-TYPE
	SYNTAX  Counter64
	MAX-ACCESS  read-only
	STATUS  current
	DESCRIPTION
		"Packets sent from this IP address during RNAT sessions."
	::= { nsRnatPerIPStatsEntry 4 }

ipRnatTotTxSyn  OBJECT-TYPE
	SYNTAX  Counter64
	MAX-ACCESS  read-only
	STATUS  current
	DESCRIPTION
		"Requests for connections sent from this IP address during RNAT sessions."
	::= { nsRnatPerIPStatsEntry 5 }

ipRnatCurSessions  OBJECT-TYPE
	SYNTAX  Gauge32
	MAX-ACCESS  read-only
	STATUS  current
	DESCRIPTION
		"Currently active RNAT sessions started from this IP address."
	::= { nsRnatPerIPStatsEntry 6 }

nsSslVpnStatsGroup OBJECT IDENTIFIER
	::= { nsSysGroup 66 }

indexHtmlHit  OBJECT-TYPE
	SYNTAX  Counter64
	MAX-ACCESS  read-only
	STATUS  current
	DESCRIPTION
		"Total number of login-page request received by SSLVPN server."
	::= { nsSslVpnStatsGroup 1 }

indexHtmlNoServed  OBJECT-TYPE
	SYNTAX  Counter64
	MAX-ACCESS  read-only
	STATUS  current
	DESCRIPTION
		"Number of times login-page has not been delivered by SSLVPN server."
	::= { nsSslVpnStatsGroup 2 }

cfgHtmlServed  OBJECT-TYPE
	SYNTAX  Counter64
	MAX-ACCESS  read-only
	STATUS  current
	DESCRIPTION
		"Total number of SSLVPN-client configuration request received by SSLVPN-server. In response to this SSLVPN-server returns information to configure SSLVPN-client."
	::= { nsSslVpnStatsGroup 3 }

dnsReqHit  OBJECT-TYPE
	SYNTAX  Counter64
	MAX-ACCESS  read-only
	STATUS  current
	DESCRIPTION
		"Total number of DNS query(s) resolved by SSLVPN server."
	::= { nsSslVpnStatsGroup 4 }

winsRequestHit  OBJECT-TYPE
	SYNTAX  Counter64
	MAX-ACCESS  read-only
	STATUS  current
	DESCRIPTION
		"Total number of WINS query(s) resolved by SSLVPN server."
	::= { nsSslVpnStatsGroup 5 }

csRequestHit  OBJECT-TYPE
	SYNTAX  Counter64
	MAX-ACCESS  read-only
	STATUS  current
	DESCRIPTION
		"Total number of SSLVPN tunnels created between SSLVPN client and server."
	::= { nsSslVpnStatsGroup 6 }

csNonHttpProbeHit  OBJECT-TYPE
	SYNTAX  Counter64
	MAX-ACCESS  read-only
	STATUS  current
	DESCRIPTION
		"Number of probes from NetScaler to backend non-HTTP servers. The backend servers are those servers which has been accessed by VPN client. This is an application debug counter."
	::= { nsSslVpnStatsGroup 7 }

csHttpProbeHit  OBJECT-TYPE
	SYNTAX  Counter64
	MAX-ACCESS  read-only
	STATUS  current
	DESCRIPTION
		"Number of probes from NetScaler to backend HTTP server. The backend servers are those servers which has been accessed by VPN client. This is an application debug counter."
	::= { nsSslVpnStatsGroup 8 }

totalCsConnSucc  OBJECT-TYPE
	SYNTAX  Counter64
	MAX-ACCESS  read-only
	STATUS  current
	DESCRIPTION
		"Number of successful probes to backend servers (both HTTP and non-HTTP). This is an application debug counter."
	::= { nsSslVpnStatsGroup 9 }

totalFsRequest  OBJECT-TYPE
	SYNTAX  Counter64
	MAX-ACCESS  read-only
	STATUS  current
	DESCRIPTION
		"Total number of file-system request received by SSLVPN server."
	::= { nsSslVpnStatsGroup 10 }

iipDisabledMIPdisabled  OBJECT-TYPE
	SYNTAX  Counter64
	MAX-ACCESS  read-only
	STATUS  current
	DESCRIPTION
		"Both IIP and MIP is disabled."
	::= { nsSslVpnStatsGroup 11 }

iipFailedMIPdisabled  OBJECT-TYPE
	SYNTAX  Counter64
	MAX-ACCESS  read-only
	STATUS  current
	DESCRIPTION
		"Number of times IIP assignment failed and MIP is disabled."
	::= { nsSslVpnStatsGroup 12 }

iipDisabledMIPused  OBJECT-TYPE
	SYNTAX  Counter64
	MAX-ACCESS  read-only
	STATUS  current
	DESCRIPTION
		"Number of times MIP is used as IIP is disabled."
	::= { nsSslVpnStatsGroup 13 }

iipFailedMIPused  OBJECT-TYPE
	SYNTAX  Counter64
	MAX-ACCESS  read-only
	STATUS  current
	DESCRIPTION
		"Number of times MIP is used as IIP assignment failed."
	::= { nsSslVpnStatsGroup 14 }

socksMethReqRcvd  OBJECT-TYPE
	SYNTAX  Counter64
	MAX-ACCESS  read-only
	STATUS  current
	DESCRIPTION
		"Number of received SOCKS method request."
	::= { nsSslVpnStatsGroup 15 }

socksMethReqSent  OBJECT-TYPE
	SYNTAX  Counter64
	MAX-ACCESS  read-only
	STATUS  current
	DESCRIPTION
		"Number of sent SOCKS method request."
	::= { nsSslVpnStatsGroup 16 }

socksMethRespRcvd  OBJECT-TYPE
	SYNTAX  Counter64
	MAX-ACCESS  read-only
	STATUS  current
	DESCRIPTION
		"Number of received SOCKS method response."
	::= { nsSslVpnStatsGroup 17 }

socksMethRespSent  OBJECT-TYPE
	SYNTAX  Counter64
	MAX-ACCESS  read-only
	STATUS  current
	DESCRIPTION
		"Number of sent SOCKS method response."
	::= { nsSslVpnStatsGroup 18 }

socksConnReqRcvd  OBJECT-TYPE
	SYNTAX  Counter64
	MAX-ACCESS  read-only
	STATUS  current
	DESCRIPTION
		"Number of received SOCKS connect request."
	::= { nsSslVpnStatsGroup 19 }

socksConnReqSent  OBJECT-TYPE
	SYNTAX  Counter64
	MAX-ACCESS  read-only
	STATUS  current
	DESCRIPTION
		"Number of sent SOCKS connect request."
	::= { nsSslVpnStatsGroup 20 }

socksConnRespRcvd  OBJECT-TYPE
	SYNTAX  Counter64
	MAX-ACCESS  read-only
	STATUS  current
	DESCRIPTION
		"Number of received SOCKS connect response."
	::= { nsSslVpnStatsGroup 21 }

socksConnRespSent  OBJECT-TYPE
	SYNTAX  Counter64
	MAX-ACCESS  read-only
	STATUS  current
	DESCRIPTION
		"Number of sent SOCKS connect response."
	::= { nsSslVpnStatsGroup 22 }

socksServerError  OBJECT-TYPE
	SYNTAX  Counter64
	MAX-ACCESS  read-only
	STATUS  current
	DESCRIPTION
		"Number of SOCKS server error."
	::= { nsSslVpnStatsGroup 23 }

socksClientError  OBJECT-TYPE
	SYNTAX  Counter64
	MAX-ACCESS  read-only
	STATUS  current
	DESCRIPTION
		"Number of SOCKS client error."
	::= { nsSslVpnStatsGroup 24 }

staConnSuccess  OBJECT-TYPE
	SYNTAX  Counter64
	MAX-ACCESS  read-only
	STATUS  current
	DESCRIPTION
		"Number of STA connection success."
	::= { nsSslVpnStatsGroup 25 }

staConnFailure  OBJECT-TYPE
	SYNTAX  Counter64
	MAX-ACCESS  read-only
	STATUS  current
	DESCRIPTION
		"Number of STA connection failure."
	::= { nsSslVpnStatsGroup 26 }

cpsConnSuccess  OBJECT-TYPE
	SYNTAX  Counter64
	MAX-ACCESS  read-only
	STATUS  current
	DESCRIPTION
		"Number of CPS connection success."
	::= { nsSslVpnStatsGroup 27 }

cpsConnFailure  OBJECT-TYPE
	SYNTAX  Counter64
	MAX-ACCESS  read-only
	STATUS  current
	DESCRIPTION
		"Number of CPS connection failure."
	::= { nsSslVpnStatsGroup 28 }

staRequestSent  OBJECT-TYPE
	SYNTAX  Counter64
	MAX-ACCESS  read-only
	STATUS  current
	DESCRIPTION
		"Number of STA request sent."
	::= { nsSslVpnStatsGroup 29 }

staResponseRecvd  OBJECT-TYPE
	SYNTAX  Counter64
	MAX-ACCESS  read-only
	STATUS  current
	DESCRIPTION
		"Number of STA response received."
	::= { nsSslVpnStatsGroup 30 }

icaLicenseFailure  OBJECT-TYPE
	SYNTAX  Counter64
	MAX-ACCESS  read-only
	STATUS  current
	DESCRIPTION
		"Number of ICA license failure."
	::= { nsSslVpnStatsGroup 31 }

staRenewSent  OBJECT-TYPE
	SYNTAX  Counter64
	MAX-ACCESS  read-only
	STATUS  current
	DESCRIPTION
		"Number of STA renew requests sent."
	::= { nsSslVpnStatsGroup 32 }

staRenewRecvd  OBJECT-TYPE
	SYNTAX  Counter64
	MAX-ACCESS  read-only
	STATUS  current
	DESCRIPTION
		"Number of STA renew response received."
	::= { nsSslVpnStatsGroup 33 }

staReassErr  OBJECT-TYPE
	SYNTAX  Counter64
	MAX-ACCESS  read-only
	STATUS  current
	DESCRIPTION
		"Number of STA response reassembly errors."
	::= { nsSslVpnStatsGroup 34 }

staRnewNoClnt  OBJECT-TYPE
	SYNTAX  Counter64
	MAX-ACCESS  read-only
	STATUS  current
	DESCRIPTION
		"Number of STA renew repsonse for missing clients."
	::= { nsSslVpnStatsGroup 35 }

staRenewNoRfsh  OBJECT-TYPE
	SYNTAX  Counter64
	MAX-ACCESS  read-only
	STATUS  current
	DESCRIPTION
		"Number of STA renew response missing refesh values."
	::= { nsSslVpnStatsGroup 36 }

staValidNoClnt  OBJECT-TYPE
	SYNTAX  Counter64
	MAX-ACCESS  read-only
	STATUS  current
	DESCRIPTION
		"Number of STA validate response for clients that have already closed."
	::= { nsSslVpnStatsGroup 37 }

staValidNoEst  OBJECT-TYPE
	SYNTAX  Counter64
	MAX-ACCESS  read-only
	STATUS  current
	DESCRIPTION
		"Number of STA validate responses for clients not in TCP ESTABLISHED state."
	::= { nsSslVpnStatsGroup 38 }

staMonSent  OBJECT-TYPE
	SYNTAX  Counter64
	MAX-ACCESS  read-only
	STATUS  current
	DESCRIPTION
		"Number of STA monitor requests sent."
	::= { nsSslVpnStatsGroup 39 }

staMonRcvd  OBJECT-TYPE
	SYNTAX  Counter64
	MAX-ACCESS  read-only
	STATUS  current
	DESCRIPTION
		"Number of STA monitor responses recieved."
	::= { nsSslVpnStatsGroup 40 }

staMonSucc  OBJECT-TYPE
	SYNTAX  Counter64
	MAX-ACCESS  read-only
	STATUS  current
	DESCRIPTION
		"Number of STA monitor successful responses."
	::= { nsSslVpnStatsGroup 41 }

staMonFail  OBJECT-TYPE
	SYNTAX  Counter64
	MAX-ACCESS  read-only
	STATUS  current
	DESCRIPTION
		"Number of STA monitor failed responses."
	::= { nsSslVpnStatsGroup 42 }

nsAaaStatsGroup OBJECT IDENTIFIER
	::= { nsSysGroup 67 }

aaaAuthFail  OBJECT-TYPE
	SYNTAX  Counter64
	MAX-ACCESS  read-only
	STATUS  current
	DESCRIPTION
		"Count of authentication failures"
	::= { nsAaaStatsGroup 1 }

aaaAuthSuccess  OBJECT-TYPE
	SYNTAX  Counter64
	MAX-ACCESS  read-only
	STATUS  current
	DESCRIPTION
		"Count of authentication successes"
	::= { nsAaaStatsGroup 2 }

aaaAuthNonHttpFail  OBJECT-TYPE
	SYNTAX  Counter64
	MAX-ACCESS  read-only
	STATUS  current
	DESCRIPTION
		"Count of non HTTP connections that failed authorization"
	::= { nsAaaStatsGroup 3 }

aaaAuthOnlyHttpFail  OBJECT-TYPE
	SYNTAX  Counter64
	MAX-ACCESS  read-only
	STATUS  current
	DESCRIPTION
		"Count of HTTP connections that failed authorization"
	::= { nsAaaStatsGroup 4 }

aaaAuthNonHttpSuccess  OBJECT-TYPE
	SYNTAX  Counter64
	MAX-ACCESS  read-only
	STATUS  current
	DESCRIPTION
		"Count of non HTTP connections that succeeded authorization"
	::= { nsAaaStatsGroup 5 }

aaaAuthOnlyHttpSuccess  OBJECT-TYPE
	SYNTAX  Counter64
	MAX-ACCESS  read-only
	STATUS  current
	DESCRIPTION
		"Count of HTTP connections that succeeded authorization"
	::= { nsAaaStatsGroup 6 }

aaaTotSessions  OBJECT-TYPE
	SYNTAX  Counter64
	MAX-ACCESS  read-only
	STATUS  current
	DESCRIPTION
		"Count of all AAA sessions"
	::= { nsAaaStatsGroup 7 }

aaaTotSessionTimeout  OBJECT-TYPE
	SYNTAX  Counter64
	MAX-ACCESS  read-only
	STATUS  current
	DESCRIPTION
		"Count of AAA sessions that have timed out"
	::= { nsAaaStatsGroup 8 }

aaaCurSessions  OBJECT-TYPE
	SYNTAX  Counter64
	MAX-ACCESS  read-only
	STATUS  current
	DESCRIPTION
		"Count of current AAA sessions"
	::= { nsAaaStatsGroup 9 }

nsGlobalConfigSettings OBJECT IDENTIFIER
	::= { nsSysGroup 68 }

webServerHttpPorts  OBJECT-TYPE
	SYNTAX  OCTET STRING
	MAX-ACCESS  read-only
	STATUS  current
	DESCRIPTION
		"The HTTP ports on the Web server. System performs  connection off-load for any client request that has a destination port matching one of these configured  ports. "
	::= { nsGlobalConfigSettings 1 }

maxTcpConnections  OBJECT-TYPE
	SYNTAX  Integer32
	MAX-ACCESS  read-only
	STATUS  current
	DESCRIPTION
		"The maximum number of connections that will be made from the system to the web server(s) attached to it. This value is applied globally to all attached servers."
	::= { nsGlobalConfigSettings 2 }

maxReqPerConnection  OBJECT-TYPE
	SYNTAX  Integer32
	MAX-ACCESS  read-only
	STATUS  current
	DESCRIPTION
		"The maximum number of requests that the system can pass on a particular connection between the system and a server attached to it. If the Value is zero, then it allows an unlimited number of requests to be passed."
	::= { nsGlobalConfigSettings 3 }

cipInsertionStatus  OBJECT-TYPE
	SYNTAX  ModeStatus
	MAX-ACCESS  read-only
	STATUS  current
	DESCRIPTION
		"This represents the option  to control (enable or disable) the insertion of the actual client IP address into the  HTTP  header  request  passed from  the  client  to  any of the servers attached to the system. The passed address can then be accessed through a minor  modification to the server. If cipHeader is specified, it will be used as the client IP header. If it is not specified, then the value that has been set by the  set  ns  config  CLI  command will be used as the client IP header."
	::= { nsGlobalConfigSettings 4 }

cipInsertionHeader  OBJECT-TYPE
	SYNTAX  OCTET STRING
	MAX-ACCESS  read-only
	STATUS  current
	DESCRIPTION
		"This represents the text that will be used as the client IP header."
	::= { nsGlobalConfigSettings 5 }

cookieVersionInserted  OBJECT-TYPE
	SYNTAX  Integer32
	MAX-ACCESS  read-only
	STATUS  current
	DESCRIPTION
		"The version of the cookie inserted by the system."
	::= { nsGlobalConfigSettings 6 }

minPathMTU  OBJECT-TYPE
	SYNTAX  Integer32
	MAX-ACCESS  read-only
	STATUS  current
	DESCRIPTION
		"The minimum Path MTU of the system."
	::= { nsGlobalConfigSettings 7 }

mtuEntryTimeoutValue  OBJECT-TYPE
	SYNTAX  TimeTicks
	MAX-ACCESS  read-only
	STATUS  current
	DESCRIPTION
		"The timeout value of MTU entries."
	::= { nsGlobalConfigSettings 8 }

ftpPortRange  OBJECT-TYPE
	SYNTAX  OCTET STRING
	MAX-ACCESS  read-only
	STATUS  current
	DESCRIPTION
		"The Port range configured for FTP services."
	::= { nsGlobalConfigSettings 9 }

nsPolicyInfrastructureGroup OBJECT IDENTIFIER
	::= { nsSysGroup 69 }

piPolicyTable  OBJECT-TYPE
	SYNTAX  SEQUENCE OF PiPolicyEntry
	MAX-ACCESS  not-accessible
	STATUS  current
	DESCRIPTION
		"The policy relationship table"
	::= { nsPolicyInfrastructureGroup 1 }

piPolicyEntry  OBJECT-TYPE
	SYNTAX  PiPolicyEntry
	MAX-ACCESS  not-accessible
	STATUS  current
	DESCRIPTION
		"..."
	INDEX { piPolName   }
	::= { piPolicyTable 1 }

PiPolicyEntry ::= SEQUENCE {
	piPolName  OCTET STRING,
	piPolicyHits  Counter64,
	piPolicyUndefHits  Counter64
}

piPolName  OBJECT-TYPE
	SYNTAX  OCTET STRING
	MAX-ACCESS  read-only
	STATUS  current
	DESCRIPTION
		"Name of the PI policy"
	::= { piPolicyEntry 1 }

piPolicyHits  OBJECT-TYPE
	SYNTAX  Counter64
	MAX-ACCESS  read-only
	STATUS  current
	DESCRIPTION
		"Number of hits on the policy"
	::= { piPolicyEntry 2 }

piPolicyUndefHits  OBJECT-TYPE
	SYNTAX  Counter64
	MAX-ACCESS  read-only
	STATUS  current
	DESCRIPTION
		"Number of undef hits on the policy"
	::= { piPolicyEntry 3 }

nsSvcGroup OBJECT IDENTIFIER
	::= { rs9000 2 }

serviceTable  OBJECT-TYPE
	SYNTAX  SEQUENCE OF ServiceEntry
	MAX-ACCESS  not-accessible
	STATUS  current
	DESCRIPTION
		"The netscaler services table"
	::= { nsSvcGroup 1 }

serviceEntry  OBJECT-TYPE
	SYNTAX  ServiceEntry
	MAX-ACCESS  not-accessible
	STATUS  current
	DESCRIPTION
		"..."
	INDEX { svcServiceName   }
	::= { serviceTable 1 }

ServiceEntry ::= SEQUENCE {
	svcServiceName  OCTET STRING,
	svcIpAddress  IpAddress,
	svcPort  Integer32,
	svcServiceType  EntityProtocolType,
	svcState  EntityState,
	svcMaxReqPerConn  Integer32,
	svcAvgTransactionTime  TimeTicks,
	svcEstablishedConn  Counter32,
	svcActiveConn  Gauge32,
	svcSurgeCount  Counter32,
	svcTotalRequestsLow  Counter32,
	svcTotalRequestsHigh  Counter32,
	svcTotalRequestBytesLow  Counter32,
	svcTotalRequestBytesHigh  Counter32,
	svcTotalResponsesLow  Counter32,
	svcTotalResponsesHigh  Counter32,
	svcTotalResponseBytesLow  Counter32,
	svcTotalResponseBytesHigh  Counter32,
	svcTotalPktsRecvdLow  Counter32,
	svcTotalPktsRecvdHigh  Counter32,
	svcTotalPktsSentLow  Counter32,
	svcTotalPktsSentHigh  Counter32,
	svcTotalSynsRecvdLow  Counter32,
	svcTotalSynsRecvdHigh  Counter32,
	svcTotalRequests  Counter64,
	svcTotalRequestBytes  Counter64,
	svcTotalResponses  Counter64,
	svcTotalResponseBytes  Counter64,
	svcTotalPktsRecvd  Counter64,
	svcTotalPktsSent  Counter64,
	svcTotalSynsRecvd  Counter64,
	svcGslbSiteName  OCTET STRING,
	svcAvgSvrTTFB  Gauge32,
	svctotalJsTransactions  Counter64,
	svcdosQDepth  Counter32,
	svcCurClntConnections  Gauge32,
	svcRequestRate  OCTET STRING,
	svcRxBytesRate  OCTET STRING,
	svcTxBytesRate  OCTET STRING,
	svcSynfloodRate  OCTET STRING,
	svcServiceFullName  OCTET STRING,
	svcTicksSinceLastStateChange  TimeTicks,
	svcInetAddressType  InetAddressType,
	svcInetAddress  InetAddress,
	svcTotalClients  Counter64,
	svcTotalServers  Counter64,
	svcMaxClients  Integer32,
	svcActiveTransactions  Gauge32
}

svcServiceName  OBJECT-TYPE
	SYNTAX  OCTET STRING
	MAX-ACCESS  read-only
	STATUS  current
	DESCRIPTION
		"The name of the service."
	::= { serviceEntry 1 }

svcIpAddress  OBJECT-TYPE
	SYNTAX  IpAddress
	MAX-ACCESS  read-only
	STATUS  current
	DESCRIPTION
		"The ip address at which the service is running."
	::= { serviceEntry 2 }

svcPort  OBJECT-TYPE
	SYNTAX  Integer32
	MAX-ACCESS  read-only
	STATUS  current
	DESCRIPTION
		"The port at which the service is running."
	::= { serviceEntry 3 }

svcServiceType  OBJECT-TYPE
	SYNTAX  EntityProtocolType
	MAX-ACCESS  read-only
	STATUS  current
	DESCRIPTION
		"The protocol type of the service"
	::= { serviceEntry 4 }

svcState  OBJECT-TYPE
	SYNTAX  EntityState
	MAX-ACCESS  read-only
	STATUS  current
	DESCRIPTION
		"Current state of the server."
	::= { serviceEntry 5 }

svcMaxReqPerConn  OBJECT-TYPE
	SYNTAX  Integer32
	MAX-ACCESS  read-only
	STATUS  current
	DESCRIPTION
		"The maximum requests per connection allowed on this service. "
	::= { serviceEntry 6 }

svcAvgTransactionTime  OBJECT-TYPE
	SYNTAX  TimeTicks
	MAX-ACCESS  read-only
	STATUS  current
	DESCRIPTION
		"Average transaction time between netscaler and the service behind it."
	::= { serviceEntry 7 }

svcEstablishedConn  OBJECT-TYPE
	SYNTAX  Counter32
	MAX-ACCESS  read-only
	STATUS  current
	DESCRIPTION
		"The number of established connections."
	::= { serviceEntry 8 }

svcActiveConn  OBJECT-TYPE
	SYNTAX  Gauge32
	MAX-ACCESS  read-only
	STATUS  current
	DESCRIPTION
		"The number of established connections that are currently active. "
	::= { serviceEntry 9 }

svcSurgeCount  OBJECT-TYPE
	SYNTAX  Counter32
	MAX-ACCESS  read-only
	STATUS  current
	DESCRIPTION
		"The number requests in the surge queue."
	::= { serviceEntry 10 }

svcTotalRequestsLow  OBJECT-TYPE
	SYNTAX  Counter32
	MAX-ACCESS  read-only
	STATUS  obsolete
	DESCRIPTION
		"...OBSOLETE"
	::= { serviceEntry 11 }

svcTotalRequestsHigh  OBJECT-TYPE
	SYNTAX  Counter32
	MAX-ACCESS  read-only
	STATUS  obsolete
	DESCRIPTION
		"...OBSOLETE"
	::= { serviceEntry 12 }

svcTotalRequestBytesLow  OBJECT-TYPE
	SYNTAX  Counter32
	MAX-ACCESS  read-only
	STATUS  obsolete
	DESCRIPTION
		"...OBSOLETE"
	::= { serviceEntry 13 }

svcTotalRequestBytesHigh  OBJECT-TYPE
	SYNTAX  Counter32
	MAX-ACCESS  read-only
	STATUS  obsolete
	DESCRIPTION
		"...OBSOLETE"
	::= { serviceEntry 14 }

svcTotalResponsesLow  OBJECT-TYPE
	SYNTAX  Counter32
	MAX-ACCESS  read-only
	STATUS  obsolete
	DESCRIPTION
		"...OBSOLETE"
	::= { serviceEntry 15 }

svcTotalResponsesHigh  OBJECT-TYPE
	SYNTAX  Counter32
	MAX-ACCESS  read-only
	STATUS  obsolete
	DESCRIPTION
		"...OBSOLETE"
	::= { serviceEntry 16 }

svcTotalResponseBytesLow  OBJECT-TYPE
	SYNTAX  Counter32
	MAX-ACCESS  read-only
	STATUS  obsolete
	DESCRIPTION
		"...OBSOLETE"
	::= { serviceEntry 17 }

svcTotalResponseBytesHigh  OBJECT-TYPE
	SYNTAX  Counter32
	MAX-ACCESS  read-only
	STATUS  obsolete
	DESCRIPTION
		"...OBSOLETE"
	::= { serviceEntry 18 }

svcTotalPktsRecvdLow  OBJECT-TYPE
	SYNTAX  Counter32
	MAX-ACCESS  read-only
	STATUS  obsolete
	DESCRIPTION
		"...OBSOLETE"
	::= { serviceEntry 19 }

svcTotalPktsRecvdHigh  OBJECT-TYPE
	SYNTAX  Counter32
	MAX-ACCESS  read-only
	STATUS  obsolete
	DESCRIPTION
		"...OBSOLETE"
	::= { serviceEntry 20 }

svcTotalPktsSentLow  OBJECT-TYPE
	SYNTAX  Counter32
	MAX-ACCESS  read-only
	STATUS  obsolete
	DESCRIPTION
		"...OBSOLETE"
	::= { serviceEntry 21 }

svcTotalPktsSentHigh  OBJECT-TYPE
	SYNTAX  Counter32
	MAX-ACCESS  read-only
	STATUS  obsolete
	DESCRIPTION
		"...OBSOLETE"
	::= { serviceEntry 22 }

svcTotalSynsRecvdLow  OBJECT-TYPE
	SYNTAX  Counter32
	MAX-ACCESS  read-only
	STATUS  obsolete
	DESCRIPTION
		"...OBSOLETE"
	::= { serviceEntry 23 }

svcTotalSynsRecvdHigh  OBJECT-TYPE
	SYNTAX  Counter32
	MAX-ACCESS  read-only
	STATUS  obsolete
	DESCRIPTION
		"...OBSOLETE"
	::= { serviceEntry 24 }

svcTotalRequests  OBJECT-TYPE
	SYNTAX  Counter64
	MAX-ACCESS  read-only
	STATUS  current
	DESCRIPTION
		"The total number of requests received on this service/vserver(This is applicable for HTTP/SSL servicetype)."
	::= { serviceEntry 30 }

svcTotalRequestBytes  OBJECT-TYPE
	SYNTAX  Counter64
	MAX-ACCESS  read-only
	STATUS  current
	DESCRIPTION
		"The total number of request bytes received on this service/vserver."
	::= { serviceEntry 31 }

svcTotalResponses  OBJECT-TYPE
	SYNTAX  Counter64
	MAX-ACCESS  read-only
	STATUS  current
	DESCRIPTION
		"Number of responses received on this service/vserver(This is applicable for HTTP/SSL servicetype)."
	::= { serviceEntry 32 }

svcTotalResponseBytes  OBJECT-TYPE
	SYNTAX  Counter64
	MAX-ACCESS  read-only
	STATUS  current
	DESCRIPTION
		"Number of response bytes received on this service/vserver."
	::= { serviceEntry 33 }

svcTotalPktsRecvd  OBJECT-TYPE
	SYNTAX  Counter64
	MAX-ACCESS  read-only
	STATUS  current
	DESCRIPTION
		"The total number of packets received on this service/vserver."
	::= { serviceEntry 34 }

svcTotalPktsSent  OBJECT-TYPE
	SYNTAX  Counter64
	MAX-ACCESS  read-only
	STATUS  current
	DESCRIPTION
		"  The total number of packets sent. "
	::= { serviceEntry 35 }

svcTotalSynsRecvd  OBJECT-TYPE
	SYNTAX  Counter64
	MAX-ACCESS  read-only
	STATUS  current
	DESCRIPTION
		"The total number of syns received from clients on this service/vserver."
	::= { serviceEntry 36 }

svcGslbSiteName  OBJECT-TYPE
	SYNTAX  OCTET STRING
	MAX-ACCESS  read-only
	STATUS  current
	DESCRIPTION
		"The name of the gslb site on which this service is defined."
	::= { serviceEntry 37 }

svcAvgSvrTTFB  OBJECT-TYPE
	SYNTAX  Gauge32
	MAX-ACCESS  read-only
	STATUS  current
	DESCRIPTION
		"The average TTFB between the netscaler and the server."
	::= { serviceEntry 38 }

svctotalJsTransactions  OBJECT-TYPE
	SYNTAX  Counter64
	MAX-ACCESS  read-only
	STATUS  current
	DESCRIPTION
		" Total number of javascripts sent to geniune clients. "
	::= { serviceEntry 39 }

svcdosQDepth  OBJECT-TYPE
	SYNTAX  Counter32
	MAX-ACCESS  read-only
	STATUS  current
	DESCRIPTION
		"The number of geniune client on this service. "
	::= { serviceEntry 40 }

svcCurClntConnections  OBJECT-TYPE
	SYNTAX  Gauge32
	MAX-ACCESS  read-only
	STATUS  current
	DESCRIPTION
		"The number of current client connections."
	::= { serviceEntry 41 }

svcRequestRate  OBJECT-TYPE
	SYNTAX  OCTET STRING
	MAX-ACCESS  read-only
	STATUS  current
	DESCRIPTION
		"This represents the request rate in requests per second for this service/vserver."
	::= { serviceEntry 42 }

svcRxBytesRate  OBJECT-TYPE
	SYNTAX  OCTET STRING
	MAX-ACCESS  read-only
	STATUS  current
	DESCRIPTION
		"This represents the request rate in bytes per second fot this service/vserver."
	::= { serviceEntry 43 }

svcTxBytesRate  OBJECT-TYPE
	SYNTAX  OCTET STRING
	MAX-ACCESS  read-only
	STATUS  current
	DESCRIPTION
		"This represents the response rate in bytes per second fot this service/vserver."
	::= { serviceEntry 44 }

svcSynfloodRate  OBJECT-TYPE
	SYNTAX  OCTET STRING
	MAX-ACCESS  read-only
	STATUS  current
	DESCRIPTION
		"This represents the rate of unacknowledged SYNs for this service/vserver."
	::= { serviceEntry 45 }

svcServiceFullName  OBJECT-TYPE
	SYNTAX  OCTET STRING
	MAX-ACCESS  read-only
	STATUS  current
	DESCRIPTION
		"The name of the service."
	::= { serviceEntry 46 }

svcTicksSinceLastStateChange  OBJECT-TYPE
	SYNTAX  TimeTicks
	MAX-ACCESS  read-only
	STATUS  current
	DESCRIPTION
		"Time (in 10 milliseconds) since the last state change."
	::= { serviceEntry 47 }

svcInetAddressType  OBJECT-TYPE
	SYNTAX  InetAddressType
	MAX-ACCESS  read-only
	STATUS  current
	DESCRIPTION
		"The address type of svcInetAddress"
	::= { serviceEntry 48 }

svcInetAddress  OBJECT-TYPE
	SYNTAX  InetAddress
	MAX-ACCESS  read-only
	STATUS  current
	DESCRIPTION
		"The Internet address at which the service is running."
	::= { serviceEntry 49 }

svcTotalClients  OBJECT-TYPE
	SYNTAX  Counter64
	MAX-ACCESS  read-only
	STATUS  current
	DESCRIPTION
		"The total number of established client connections."
	::= { serviceEntry 50 }

svcTotalServers  OBJECT-TYPE
	SYNTAX  Counter64
	MAX-ACCESS  read-only
	STATUS  current
	DESCRIPTION
		"The total number of established server connections."
	::= { serviceEntry 51 }

svcMaxClients  OBJECT-TYPE
	SYNTAX  Integer32
	MAX-ACCESS  read-only
	STATUS  current
	DESCRIPTION
		"The maximum open connections allowed on this service."
	::= { serviceEntry 52 }

svcActiveTransactions  OBJECT-TYPE
	SYNTAX  Gauge32
	MAX-ACCESS  read-only
	STATUS  current
	DESCRIPTION
		"The number of Active Transactions handled by this service(Includes the surgeQ count also)."
	::= { serviceEntry 53 }

serverTable  OBJECT-TYPE
	SYNTAX  SEQUENCE OF ServerEntry
	MAX-ACCESS  not-accessible
	STATUS  current
	DESCRIPTION
		"The servers table."
	::= { nsSvcGroup 2 }

serverEntry  OBJECT-TYPE
	SYNTAX  ServerEntry
	MAX-ACCESS  not-accessible
	STATUS  current
	DESCRIPTION
		"..."
	INDEX { serverName   }
	::= { serverTable 1 }

ServerEntry ::= SEQUENCE {
	serverName  OCTET STRING,
	serverIpAddress  IpAddress,
	serverState  EntityState,
	serverDelay  Integer32,
	serverFullName  OCTET STRING,
	serverInetAddressType  InetAddressType,
	serverInetAddress  InetAddress
}

serverName  OBJECT-TYPE
	SYNTAX  OCTET STRING
	MAX-ACCESS  read-only
	STATUS  current
	DESCRIPTION
		"The name of the server."
	::= { serverEntry 1 }

serverIpAddress  OBJECT-TYPE
	SYNTAX  IpAddress
	MAX-ACCESS  read-only
	STATUS  current
	DESCRIPTION
		"The IP address of the server."
	::= { serverEntry 2 }

serverState  OBJECT-TYPE
	SYNTAX  EntityState
	MAX-ACCESS  read-write
	STATUS  current
	DESCRIPTION
		"The state of the server."
	::= { serverEntry 3 }

serverDelay  OBJECT-TYPE
	SYNTAX  Integer32
	MAX-ACCESS  read-write
	STATUS  current
	DESCRIPTION
		"Specifies time in seconds after which all services in this server are brought down."
	::= { serverEntry 4 }

serverFullName  OBJECT-TYPE
	SYNTAX  OCTET STRING
	MAX-ACCESS  read-only
	STATUS  current
	DESCRIPTION
		"The name of the server."
	::= { serverEntry 5 }

serverInetAddressType  OBJECT-TYPE
	SYNTAX  InetAddressType
	MAX-ACCESS  read-only
	STATUS  current
	DESCRIPTION
		"The address type of serverInetAddress"
	::= { serverEntry 6 }

serverInetAddress  OBJECT-TYPE
	SYNTAX  InetAddress
	MAX-ACCESS  read-only
	STATUS  current
	DESCRIPTION
		"The Internet address of the server."
	::= { serverEntry 7 }

serviceScpolicyTable  OBJECT-TYPE
	SYNTAX  SEQUENCE OF ServiceScpolicyEntry
	MAX-ACCESS  not-accessible
	STATUS  current
	DESCRIPTION
		"The service sure connect policy relationship table"
	::= { nsSvcGroup 3 }

serviceScpolicyEntry  OBJECT-TYPE
	SYNTAX  ServiceScpolicyEntry
	MAX-ACCESS  not-accessible
	STATUS  current
	DESCRIPTION
		"..."
	INDEX { svcServiceName , scPolicyName }
	::= { serviceScpolicyTable 1 }

ServiceScpolicyEntry ::= SEQUENCE {
	svcscpolicyPrimaryIPAddress  IpAddress,
	svcscpolicyPrimaryPort  Integer32,
	svcscpolicyDesIpAddress  IpAddress,
	svcscpolicyDestPort  Integer32,
	svcscpolicyAvgServerTransactionTime  Gauge32,
	svcscpolicyTotClientTransaction  Counter64,
	svcscpolicyTotOpenConn  Counter32,
	svcscpolicydesIpAddress  IpAddress,
	svcscpolicydestPort  Integer32,
	svcscpolicyavgServerTransactionTime  Gauge32,
	svcscpolicytotClientTransaction  Counter64,
	svcscpolicytotOpenConn  Gauge32,
	svcscpolicyscPhysicalServiceIP  IpAddress,
	svcscpolicyscPhysicalServicePort  Integer32,
	svcscpolicyscCurrentWaitingTime  Gauge32,
	svcscpolicyscCurrentClientConnections  Gauge32,
	svcscpolicyscTotalClientConnections  Counter64,
	svcscpolicyscTotalServerConnections  Counter64,
	svcscpolicyscTotalRequestsReceived  Counter64,
	svcscpolicyscTotalRequestBytes  Counter64,
	svcscpolicyscTotalResponsesReceived  Counter64,
	svcscpolicyscTotalResponseBytes  Counter64,
	svcscpolicyscCurrentSurgeQClients  Gauge32,
	svcscpolicyscCurrentWaitingClients  Gauge32,
	svcscpolicyscTotalServerTransactions  Counter64,
	svcscpolicyscTotalServerTTFBTransactions  Counter64,
	svcscpolicyscTotalServerTTLB  Counter64,
	svcscpolicyscTotalClientTTLB  Counter64,
	svcscpolicyscTotalServerTTFB  Counter64,
	svcscpolicyscAverageClientTTLB  Gauge32,
	svcscpolicyscAverageServerTTFB  Gauge32
}

svcscpolicyPrimaryIPAddress  OBJECT-TYPE
	SYNTAX  IpAddress
	MAX-ACCESS  read-only
	STATUS  current
	DESCRIPTION
		"The ip address of the vserver/service to which the scpolicy is bound."
	::= { serviceScpolicyEntry 3 }

svcscpolicyPrimaryPort  OBJECT-TYPE
	SYNTAX  Integer32
	MAX-ACCESS  read-only
	STATUS  current
	DESCRIPTION
		"The port of the vserver/service to which the scpolicy is bound."
	::= { serviceScpolicyEntry 4 }

svcscpolicyDesIpAddress  OBJECT-TYPE
	SYNTAX  IpAddress
	MAX-ACCESS  read-only
	STATUS  obsolete
	DESCRIPTION
		"...OBSOLETE"
	::= { serviceScpolicyEntry 5 }

svcscpolicyDestPort  OBJECT-TYPE
	SYNTAX  Integer32
	MAX-ACCESS  read-only
	STATUS  obsolete
	DESCRIPTION
		"...OBSOLETE"
	::= { serviceScpolicyEntry 6 }

svcscpolicyAvgServerTransactionTime  OBJECT-TYPE
	SYNTAX  Gauge32
	MAX-ACCESS  read-only
	STATUS  obsolete
	DESCRIPTION
		"...OBSOLETE"
	::= { serviceScpolicyEntry 7 }

svcscpolicyTotClientTransaction  OBJECT-TYPE
	SYNTAX  Counter64
	MAX-ACCESS  read-only
	STATUS  obsolete
	DESCRIPTION
		"...OBSOLETE"
	::= { serviceScpolicyEntry 8 }

svcscpolicyTotOpenConn  OBJECT-TYPE
	SYNTAX  Counter32
	MAX-ACCESS  read-only
	STATUS  obsolete
	DESCRIPTION
		"...OBSOLETE"
	::= { serviceScpolicyEntry 9 }

svcscpolicydesIpAddress  OBJECT-TYPE
	SYNTAX  IpAddress
	MAX-ACCESS  read-only
	STATUS  current
	DESCRIPTION
		"IP address of destination physical service."
	::= { serviceScpolicyEntry 10 }

svcscpolicydestPort  OBJECT-TYPE
	SYNTAX  Integer32
	MAX-ACCESS  read-only
	STATUS  current
	DESCRIPTION
		"Port number of destination physical service."
	::= { serviceScpolicyEntry 11 }

svcscpolicyavgServerTransactionTime  OBJECT-TYPE
	SYNTAX  Gauge32
	MAX-ACCESS  read-only
	STATUS  current
	DESCRIPTION
		"Average Server transaction time."
	::= { serviceScpolicyEntry 12 }

svcscpolicytotClientTransaction  OBJECT-TYPE
	SYNTAX  Counter64
	MAX-ACCESS  read-only
	STATUS  current
	DESCRIPTION
		"Total number of client transactions for this policy."
	::= { serviceScpolicyEntry 13 }

svcscpolicytotOpenConn  OBJECT-TYPE
	SYNTAX  Gauge32
	MAX-ACCESS  read-only
	STATUS  current
	DESCRIPTION
		"Total number of open connections for this policy."
	::= { serviceScpolicyEntry 14 }

svcscpolicyscPhysicalServiceIP  OBJECT-TYPE
	SYNTAX  IpAddress
	MAX-ACCESS  read-only
	STATUS  current
	DESCRIPTION
		"The IP address of the physical service for which this statistics is maintained."
	::= { serviceScpolicyEntry 15 }

svcscpolicyscPhysicalServicePort  OBJECT-TYPE
	SYNTAX  Integer32
	MAX-ACCESS  read-only
	STATUS  current
	DESCRIPTION
		"The port of the physical service for which this statistics is maintained."
	::= { serviceScpolicyEntry 16 }

svcscpolicyscCurrentWaitingTime  OBJECT-TYPE
	SYNTAX  Gauge32
	MAX-ACCESS  read-only
	STATUS  current
	DESCRIPTION
		"This counter gives the value of the currently estimated waiting time for the configured URL."
	::= { serviceScpolicyEntry 17 }

svcscpolicyscCurrentClientConnections  OBJECT-TYPE
	SYNTAX  Gauge32
	MAX-ACCESS  read-only
	STATUS  current
	DESCRIPTION
		"This counter gives the number of clients that were allowed a server connection for this policy."
	::= { serviceScpolicyEntry 18 }

svcscpolicyscTotalClientConnections  OBJECT-TYPE
	SYNTAX  Counter64
	MAX-ACCESS  read-only
	STATUS  current
	DESCRIPTION
		"This counter gives the total number of clients that were allowed a server connection for this policy."
	::= { serviceScpolicyEntry 19 }

svcscpolicyscTotalServerConnections  OBJECT-TYPE
	SYNTAX  Counter64
	MAX-ACCESS  read-only
	STATUS  current
	DESCRIPTION
		"This counter gives the total number of server connections that were established for this policy."
	::= { serviceScpolicyEntry 20 }

svcscpolicyscTotalRequestsReceived  OBJECT-TYPE
	SYNTAX  Counter64
	MAX-ACCESS  read-only
	STATUS  current
	DESCRIPTION
		"This counter gives the total number of requests received for this policy."
	::= { serviceScpolicyEntry 21 }

svcscpolicyscTotalRequestBytes  OBJECT-TYPE
	SYNTAX  Counter64
	MAX-ACCESS  read-only
	STATUS  current
	DESCRIPTION
		"This counter gives the total number of request bytes received for this policy."
	::= { serviceScpolicyEntry 22 }

svcscpolicyscTotalResponsesReceived  OBJECT-TYPE
	SYNTAX  Counter64
	MAX-ACCESS  read-only
	STATUS  current
	DESCRIPTION
		"This counter gives the total number of server responses received for this policy."
	::= { serviceScpolicyEntry 23 }

svcscpolicyscTotalResponseBytes  OBJECT-TYPE
	SYNTAX  Counter64
	MAX-ACCESS  read-only
	STATUS  current
	DESCRIPTION
		"This counter gives the total number of response bytes received for this policy."
	::= { serviceScpolicyEntry 24 }

svcscpolicyscCurrentSurgeQClients  OBJECT-TYPE
	SYNTAX  Gauge32
	MAX-ACCESS  read-only
	STATUS  current
	DESCRIPTION
		"This counter gives the number of clients that matched the SC policy but are in the surge queue."
	::= { serviceScpolicyEntry 25 }

svcscpolicyscCurrentWaitingClients  OBJECT-TYPE
	SYNTAX  Gauge32
	MAX-ACCESS  read-only
	STATUS  current
	DESCRIPTION
		"This counter gives the current number of SC priority clients that are waiting for a server connection for this policy."
	::= { serviceScpolicyEntry 26 }

svcscpolicyscTotalServerTransactions  OBJECT-TYPE
	SYNTAX  Counter64
	MAX-ACCESS  read-only
	STATUS  current
	DESCRIPTION
		"This counter gives the number of 200 OK responses received from the server for this policy."
	::= { serviceScpolicyEntry 27 }

svcscpolicyscTotalServerTTFBTransactions  OBJECT-TYPE
	SYNTAX  Counter64
	MAX-ACCESS  read-only
	STATUS  current
	DESCRIPTION
		"This counter gives the number of TTFB transcations from the server for this policy."
	::= { serviceScpolicyEntry 28 }

svcscpolicyscTotalServerTTLB  OBJECT-TYPE
	SYNTAX  Counter64
	MAX-ACCESS  read-only
	STATUS  current
	DESCRIPTION
		"This counter gives the server TTLB calculated for this policy."
	::= { serviceScpolicyEntry 29 }

svcscpolicyscTotalClientTTLB  OBJECT-TYPE
	SYNTAX  Counter64
	MAX-ACCESS  read-only
	STATUS  current
	DESCRIPTION
		"This counter gives the client TTLB calculated for this policy."
	::= { serviceScpolicyEntry 30 }

svcscpolicyscTotalServerTTFB  OBJECT-TYPE
	SYNTAX  Counter64
	MAX-ACCESS  read-only
	STATUS  current
	DESCRIPTION
		"This counter gives the server TTFB calculated for this policy."
	::= { serviceScpolicyEntry 31 }

svcscpolicyscAverageClientTTLB  OBJECT-TYPE
	SYNTAX  Gauge32
	MAX-ACCESS  read-only
	STATUS  current
	DESCRIPTION
		"This counter gives the average value of the client TTLB for this policy."
	::= { serviceScpolicyEntry 32 }

svcscpolicyscAverageServerTTFB  OBJECT-TYPE
	SYNTAX  Gauge32
	MAX-ACCESS  read-only
	STATUS  current
	DESCRIPTION
		"This counter gives the average value of the server TTFB for this policy."
	::= { serviceScpolicyEntry 33 }

serviceAdvanceSslConfigTable  OBJECT-TYPE
	SYNTAX  SEQUENCE OF ServiceAdvanceSslConfigEntry
	MAX-ACCESS  not-accessible
	STATUS  current
	DESCRIPTION
		"The service advance SSL configuration"
	::= { nsSvcGroup 4 }

serviceAdvanceSslConfigEntry  OBJECT-TYPE
	SYNTAX  ServiceAdvanceSslConfigEntry
	MAX-ACCESS  not-accessible
	STATUS  current
	DESCRIPTION
		"..."
	INDEX { svcServiceName   }
	::= { serviceAdvanceSslConfigTable 1 }

ServiceAdvanceSslConfigEntry ::= SEQUENCE {
	svcSslDH  AdminStatus,
	svcSslDHCount  Integer32,
	svcSslDHFilePath  OCTET STRING,
	svcSsleRSA  AdminStatus,
	svcSsleRSACount  Integer32,
	svcSslv2Protocol  AdminStatus,
	svcSslv3Protocol  AdminStatus,
	svcSslTLSv1Protocol  AdminStatus,
	svcSslRedirectSupport  AdminStatus,
	svcSslClearTextPort  Integer32
}

svcSslDH  OBJECT-TYPE
	SYNTAX  AdminStatus
	MAX-ACCESS  read-only
	STATUS  current
	DESCRIPTION
		"Whether DH is enabled/disabled."
	::= { serviceAdvanceSslConfigEntry 1 }

svcSslDHCount  OBJECT-TYPE
	SYNTAX  Integer32
	MAX-ACCESS  read-only
	STATUS  current
	DESCRIPTION
		"The DH refresh count to re-generate public/private key."
	::= { serviceAdvanceSslConfigEntry 2 }

svcSslDHFilePath  OBJECT-TYPE
	SYNTAX  OCTET STRING
	MAX-ACCESS  read-only
	STATUS  current
	DESCRIPTION
		"The DH file path name."
	::= { serviceAdvanceSslConfigEntry 3 }

svcSsleRSA  OBJECT-TYPE
	SYNTAX  AdminStatus
	MAX-ACCESS  read-only
	STATUS  current
	DESCRIPTION
		"The ephimeral RSA support for service."
	::= { serviceAdvanceSslConfigEntry 4 }

svcSsleRSACount  OBJECT-TYPE
	SYNTAX  Integer32
	MAX-ACCESS  read-only
	STATUS  current
	DESCRIPTION
		"The eRSA refresh count to re-generate RSA temporary key."
	::= { serviceAdvanceSslConfigEntry 5 }

svcSslv2Protocol  OBJECT-TYPE
	SYNTAX  AdminStatus
	MAX-ACCESS  read-only
	STATUS  current
	DESCRIPTION
		"The support for SSLv2 protocol for service."
	::= { serviceAdvanceSslConfigEntry 6 }

svcSslv3Protocol  OBJECT-TYPE
	SYNTAX  AdminStatus
	MAX-ACCESS  read-only
	STATUS  current
	DESCRIPTION
		"The support for SSLv3 protocol for service."
	::= { serviceAdvanceSslConfigEntry 7 }

svcSslTLSv1Protocol  OBJECT-TYPE
	SYNTAX  AdminStatus
	MAX-ACCESS  read-only
	STATUS  current
	DESCRIPTION
		"The support for  TLSv1 protocol for service."
	::= { serviceAdvanceSslConfigEntry 8 }

svcSslRedirectSupport  OBJECT-TYPE
	SYNTAX  AdminStatus
	MAX-ACCESS  read-only
	STATUS  current
	DESCRIPTION
		"The support for ssl redirect for service."
	::= { serviceAdvanceSslConfigEntry 9 }

svcSslClearTextPort  OBJECT-TYPE
	SYNTAX  Integer32
	MAX-ACCESS  read-only
	STATUS  current
	DESCRIPTION
		"The clear text port on the backend webserver."
	::= { serviceAdvanceSslConfigEntry 10 }

serviceCipherBindingTable  OBJECT-TYPE
	SYNTAX  SEQUENCE OF ServiceCipherBindingEntry
	MAX-ACCESS  not-accessible
	STATUS  current
	DESCRIPTION
		"The service cipher bindings"
	::= { nsSvcGroup 5 }

serviceCipherBindingEntry  OBJECT-TYPE
	SYNTAX  ServiceCipherBindingEntry
	MAX-ACCESS  not-accessible
	STATUS  current
	DESCRIPTION
		"..."
	INDEX { svcServiceName , svcSslCipherBindName }
	::= { serviceCipherBindingTable 1 }

ServiceCipherBindingEntry ::= SEQUENCE {
	svcSslCipherBindName  OCTET STRING,
	svcSslCipherBindDesc  OCTET STRING
}

svcSslCipherBindName  OBJECT-TYPE
	SYNTAX  OCTET STRING
	MAX-ACCESS  read-only
	STATUS  current
	DESCRIPTION
		"The cipher name bound to this service."
	::= { serviceCipherBindingEntry 1 }

svcSslCipherBindDesc  OBJECT-TYPE
	SYNTAX  OCTET STRING
	MAX-ACCESS  read-only
	STATUS  current
	DESCRIPTION
		"The Cipher description."
	::= { serviceCipherBindingEntry 2 }

serviceGlobalStatsGroup OBJECT IDENTIFIER
	::= { nsSvcGroup 6 }

svcCount  OBJECT-TYPE
	SYNTAX  Integer32
	MAX-ACCESS  read-only
	STATUS  current
	DESCRIPTION
		"Number of services in the system"
	::= { serviceGlobalStatsGroup 1 }

serverCount  OBJECT-TYPE
	SYNTAX  Integer32
	MAX-ACCESS  read-only
	STATUS  current
	DESCRIPTION
		"Number of servers in the system"
	::= { serviceGlobalStatsGroup 2 }

svcgroupCount  OBJECT-TYPE
	SYNTAX  Integer32
	MAX-ACCESS  read-only
	STATUS  current
	DESCRIPTION
		"Number of service groups in the system"
	::= { serviceGlobalStatsGroup 3 }

svcgroupmemCount  OBJECT-TYPE
	SYNTAX  Integer32
	MAX-ACCESS  read-only
	STATUS  current
	DESCRIPTION
		"Number of service group members in the system"
	::= { serviceGlobalStatsGroup 4 }

serviceGroupMemberTable  OBJECT-TYPE
	SYNTAX  SEQUENCE OF ServiceGroupMemberEntry
	MAX-ACCESS  not-accessible
	STATUS  current
	DESCRIPTION
		"The service group member bindings"
	::= { nsSvcGroup 7 }

serviceGroupMemberEntry  OBJECT-TYPE
	SYNTAX  ServiceGroupMemberEntry
	MAX-ACCESS  not-accessible
	STATUS  current
	DESCRIPTION
		"..."
	INDEX { svcGrpMemberGroupName , svcGrpMemberName }
	::= { serviceGroupMemberTable 1 }

ServiceGroupMemberEntry ::= SEQUENCE {
	svcGrpMemberGroupName  OCTET STRING,
	svcGrpMemberName  OCTET STRING,
	svcGrpMemberPrimaryIPAddress  IpAddress,
	svcGrpMemberPrimaryPort  Integer32,
	svcGrpMemberServiceType  EntityProtocolType,
	svcGrpMemberState  EntityState,
	svcGrpMemberWeight  Integer32,
	svcGrpMemberMaxReqPerConn  Integer32,
	svcGrpMemberAvgTransactionTime  TimeTicks,
	svcGrpMemberEstablishedConn  Counter32,
	svcGrpMemberActiveConn  Gauge32,
	svcGrpMemberSurgeCount  Counter32,
	svcGrpMemberTotalRequests  Counter64,
	svcGrpMemberTotalRequestBytes  Counter64,
	svcGrpMemberTotalResponses  Counter64,
	svcGrpMemberTotalResponseBytes  Counter64,
	svcGrpMemberTotalPktsRecvd  Counter64,
	svcGrpMemberTotalPktsSent  Counter64,
	svcGrpMemberTotalSynsRecvd  Counter64,
	svcGrpMemberGslbSiteName  OCTET STRING,
	svcGrpMemberAvgSvrTTFB  Gauge32,
	svcGrpMembertotalJsTransactions  Counter64,
	svcGrpMemberdosQDepth  Counter32,
	svcGrpMemberCurClntConnections  Gauge32,
	svcGrpMemberRequestRate  OCTET STRING,
	svcGrpMemberRxBytesRate  OCTET STRING,
	svcGrpMemberTxBytesRate  OCTET STRING,
	svcGrpMemberSynfloodRate  OCTET STRING,
	svcGrpMemberGroupFullName  OCTET STRING,
	svcGrpMemberFullName  OCTET STRING,
	svcGrpMemberTicksSinceLastStateChange  TimeTicks,
	svcGrpMemberPrimaryInetAddressType  InetAddressType,
	svcGrpMemberPrimaryInetAddress  InetAddress
}

svcGrpMemberGroupName  OBJECT-TYPE
	SYNTAX  OCTET STRING
	MAX-ACCESS  read-only
	STATUS  current
	DESCRIPTION
		"The name of the service Group"
	::= { serviceGroupMemberEntry 1 }

svcGrpMemberName  OBJECT-TYPE
	SYNTAX  OCTET STRING
	MAX-ACCESS  read-only
	STATUS  current
	DESCRIPTION
		"The name of the service group member"
	::= { serviceGroupMemberEntry 2 }

svcGrpMemberPrimaryIPAddress  OBJECT-TYPE
	SYNTAX  IpAddress
	MAX-ACCESS  read-only
	STATUS  current
	DESCRIPTION
		"The ip address at which the service is running."
	::= { serviceGroupMemberEntry 3 }

svcGrpMemberPrimaryPort  OBJECT-TYPE
	SYNTAX  Integer32
	MAX-ACCESS  read-only
	STATUS  current
	DESCRIPTION
		"The port of the vserver/service to which the scpolicy is bound."
	::= { serviceGroupMemberEntry 4 }

svcGrpMemberServiceType  OBJECT-TYPE
	SYNTAX  EntityProtocolType
	MAX-ACCESS  read-only
	STATUS  current
	DESCRIPTION
		"The type of the service."
	::= { serviceGroupMemberEntry 5 }

svcGrpMemberState  OBJECT-TYPE
	SYNTAX  EntityState
	MAX-ACCESS  read-only
	STATUS  current
	DESCRIPTION
		"Current state of the server."
	::= { serviceGroupMemberEntry 6 }

svcGrpMemberWeight  OBJECT-TYPE
	SYNTAX  Integer32
	MAX-ACCESS  read-write
	STATUS  current
	DESCRIPTION
		"The weight of the service group member tied to the vserver."
	::= { serviceGroupMemberEntry 7 }

svcGrpMemberMaxReqPerConn  OBJECT-TYPE
	SYNTAX  Integer32
	MAX-ACCESS  read-only
	STATUS  current
	DESCRIPTION
		"The maximum requests per connection allowed on this service. "
	::= { serviceGroupMemberEntry 8 }

svcGrpMemberAvgTransactionTime  OBJECT-TYPE
	SYNTAX  TimeTicks
	MAX-ACCESS  read-only
	STATUS  current
	DESCRIPTION
		"Average transaction time between netscaler and the service behind it."
	::= { serviceGroupMemberEntry 9 }

svcGrpMemberEstablishedConn  OBJECT-TYPE
	SYNTAX  Counter32
	MAX-ACCESS  read-only
	STATUS  current
	DESCRIPTION
		"The number of established connections."
	::= { serviceGroupMemberEntry 10 }

svcGrpMemberActiveConn  OBJECT-TYPE
	SYNTAX  Gauge32
	MAX-ACCESS  read-only
	STATUS  current
	DESCRIPTION
		"The number of established connections that are currently active. "
	::= { serviceGroupMemberEntry 11 }

svcGrpMemberSurgeCount  OBJECT-TYPE
	SYNTAX  Counter32
	MAX-ACCESS  read-only
	STATUS  current
	DESCRIPTION
		"The number requests in the surge queue."
	::= { serviceGroupMemberEntry 12 }

svcGrpMemberTotalRequests  OBJECT-TYPE
	SYNTAX  Counter64
	MAX-ACCESS  read-only
	STATUS  current
	DESCRIPTION
		"The total number of requests received on this service/vserver(This is applicable for HTTP/SSL servicetype)."
	::= { serviceGroupMemberEntry 13 }

svcGrpMemberTotalRequestBytes  OBJECT-TYPE
	SYNTAX  Counter64
	MAX-ACCESS  read-only
	STATUS  current
	DESCRIPTION
		"The total number of request bytes received on this service/vserver."
	::= { serviceGroupMemberEntry 14 }

svcGrpMemberTotalResponses  OBJECT-TYPE
	SYNTAX  Counter64
	MAX-ACCESS  read-only
	STATUS  current
	DESCRIPTION
		"Number of responses received on this service/vserver(This is applicable for HTTP/SSL servicetype)."
	::= { serviceGroupMemberEntry 15 }

svcGrpMemberTotalResponseBytes  OBJECT-TYPE
	SYNTAX  Counter64
	MAX-ACCESS  read-only
	STATUS  current
	DESCRIPTION
		"Number of response bytes received on this service/vserver."
	::= { serviceGroupMemberEntry 16 }

svcGrpMemberTotalPktsRecvd  OBJECT-TYPE
	SYNTAX  Counter64
	MAX-ACCESS  read-only
	STATUS  current
	DESCRIPTION
		"The total number of packets received on this service/vserver."
	::= { serviceGroupMemberEntry 17 }

svcGrpMemberTotalPktsSent  OBJECT-TYPE
	SYNTAX  Counter64
	MAX-ACCESS  read-only
	STATUS  current
	DESCRIPTION
		"  The total number of packets sent. "
	::= { serviceGroupMemberEntry 18 }

svcGrpMemberTotalSynsRecvd  OBJECT-TYPE
	SYNTAX  Counter64
	MAX-ACCESS  read-only
	STATUS  current
	DESCRIPTION
		"The total number of syns received from clients on this service/vserver."
	::= { serviceGroupMemberEntry 19 }

svcGrpMemberGslbSiteName  OBJECT-TYPE
	SYNTAX  OCTET STRING
	MAX-ACCESS  read-only
	STATUS  current
	DESCRIPTION
		"The name of the gslb site on which this service is defined."
	::= { serviceGroupMemberEntry 20 }

svcGrpMemberAvgSvrTTFB  OBJECT-TYPE
	SYNTAX  Gauge32
	MAX-ACCESS  read-only
	STATUS  current
	DESCRIPTION
		"The average TTFB between the netscaler and the server."
	::= { serviceGroupMemberEntry 21 }

svcGrpMembertotalJsTransactions  OBJECT-TYPE
	SYNTAX  Counter64
	MAX-ACCESS  read-only
	STATUS  current
	DESCRIPTION
		" Total number of javascripts sent to geniune clients. "
	::= { serviceGroupMemberEntry 22 }

svcGrpMemberdosQDepth  OBJECT-TYPE
	SYNTAX  Counter32
	MAX-ACCESS  read-only
	STATUS  current
	DESCRIPTION
		"The number of geniune client on this service. "
	::= { serviceGroupMemberEntry 23 }

svcGrpMemberCurClntConnections  OBJECT-TYPE
	SYNTAX  Gauge32
	MAX-ACCESS  read-only
	STATUS  current
	DESCRIPTION
		"The number of current client connections."
	::= { serviceGroupMemberEntry 24 }

svcGrpMemberRequestRate  OBJECT-TYPE
	SYNTAX  OCTET STRING
	MAX-ACCESS  read-only
	STATUS  current
	DESCRIPTION
		"This represents the request rate in requests per second for this service/vserver."
	::= { serviceGroupMemberEntry 25 }

svcGrpMemberRxBytesRate  OBJECT-TYPE
	SYNTAX  OCTET STRING
	MAX-ACCESS  read-only
	STATUS  current
	DESCRIPTION
		"This represents the request rate in bytes per second fot this service/vserver."
	::= { serviceGroupMemberEntry 26 }

svcGrpMemberTxBytesRate  OBJECT-TYPE
	SYNTAX  OCTET STRING
	MAX-ACCESS  read-only
	STATUS  current
	DESCRIPTION
		"This represents the response rate in bytes per second fot this service/vserver."
	::= { serviceGroupMemberEntry 27 }

svcGrpMemberSynfloodRate  OBJECT-TYPE
	SYNTAX  OCTET STRING
	MAX-ACCESS  read-only
	STATUS  current
	DESCRIPTION
		"This represents the rate of unacknowledged SYNs for this service/vserver."
	::= { serviceGroupMemberEntry 28 }

svcGrpMemberGroupFullName  OBJECT-TYPE
	SYNTAX  OCTET STRING
	MAX-ACCESS  read-only
	STATUS  current
	DESCRIPTION
		"The name of the service Group"
	::= { serviceGroupMemberEntry 29 }

svcGrpMemberFullName  OBJECT-TYPE
	SYNTAX  OCTET STRING
	MAX-ACCESS  read-only
	STATUS  current
	DESCRIPTION
		"The name of the service group member"
	::= { serviceGroupMemberEntry 30 }

svcGrpMemberTicksSinceLastStateChange  OBJECT-TYPE
	SYNTAX  TimeTicks
	MAX-ACCESS  read-only
	STATUS  current
	DESCRIPTION
		"Time (in 10 milliseconds) since the last state change."
	::= { serviceGroupMemberEntry 31 }

svcGrpMemberPrimaryInetAddressType  OBJECT-TYPE
	SYNTAX  InetAddressType
	MAX-ACCESS  read-only
	STATUS  current
	DESCRIPTION
		"The address type of svcGrpMemberPrimaryInetAddress"
	::= { serviceGroupMemberEntry 32 }

svcGrpMemberPrimaryInetAddress  OBJECT-TYPE
	SYNTAX  InetAddress
	MAX-ACCESS  read-only
	STATUS  current
	DESCRIPTION
		"The Internet address at which the service is running."
	::= { serviceGroupMemberEntry 33 }

serviceDospolicyTable  OBJECT-TYPE
	SYNTAX  SEQUENCE OF ServiceDospolicyEntry
	MAX-ACCESS  not-accessible
	STATUS  current
	DESCRIPTION
		"The service DOS policy relationship table"
	::= { nsSvcGroup 8 }

serviceDospolicyEntry  OBJECT-TYPE
	SYNTAX  ServiceDospolicyEntry
	MAX-ACCESS  not-accessible
	STATUS  current
	DESCRIPTION
		"..."
	INDEX { svcServiceName , dosPolicyName }
	::= { serviceDospolicyTable 1 }

ServiceDospolicyEntry ::= SEQUENCE {
	svcdospolicydosTotJSSent  Counter64,
	svcdospolicydosTotJSBytesSent  Counter64,
	svcdospolicydosTotJSRefused  Counter64,
	svcdospolicydosTotNonGetPostRequests  Counter64,
	svcdospolicydosPhysicalServiceIP  IpAddress,
	svcdospolicydosPhysicalServicePort  Integer32,
	svcdospolicydosCurrentQueueSize  Gauge32,
	svcdospolicydosCurrentJSRate  Gauge32,
	svcdospolicydosTotValidClients  Counter64,
	svcdospolicydosCurServerRespRate  Gauge32
}

svcdospolicydosTotJSSent  OBJECT-TYPE
	SYNTAX  Counter64
	MAX-ACCESS  read-only
	STATUS  current
	DESCRIPTION
		"This counter gives the total number of DOS JavaScript transactions performed for this policy."
	::= { serviceDospolicyEntry 1 }

svcdospolicydosTotJSBytesSent  OBJECT-TYPE
	SYNTAX  Counter64
	MAX-ACCESS  read-only
	STATUS  current
	DESCRIPTION
		"This counter gives the total number of DOS JS bytes sent for this policy."
	::= { serviceDospolicyEntry 2 }

svcdospolicydosTotJSRefused  OBJECT-TYPE
	SYNTAX  Counter64
	MAX-ACCESS  read-only
	STATUS  current
	DESCRIPTION
		"This counter gives the number of times the DOS JS was not sent because the set JS rate was not met for this policy."
	::= { serviceDospolicyEntry 3 }

svcdospolicydosTotNonGetPostRequests  OBJECT-TYPE
	SYNTAX  Counter64
	MAX-ACCESS  read-only
	STATUS  current
	DESCRIPTION
		"This counter gives the number of non GET, POST requests for which DOS JS was sent."
	::= { serviceDospolicyEntry 4 }

svcdospolicydosPhysicalServiceIP  OBJECT-TYPE
	SYNTAX  IpAddress
	MAX-ACCESS  read-only
	STATUS  current
	DESCRIPTION
		"IP address of the physical service to which this policy is bound."
	::= { serviceDospolicyEntry 5 }

svcdospolicydosPhysicalServicePort  OBJECT-TYPE
	SYNTAX  Integer32
	MAX-ACCESS  read-only
	STATUS  current
	DESCRIPTION
		"Port address of the physical service to which this policy is bound."
	::= { serviceDospolicyEntry 6 }

svcdospolicydosCurrentQueueSize  OBJECT-TYPE
	SYNTAX  Gauge32
	MAX-ACCESS  read-only
	STATUS  current
	DESCRIPTION
		"This counter gives the current queue size of the server to which this policy is bound."
	::= { serviceDospolicyEntry 7 }

svcdospolicydosCurrentJSRate  OBJECT-TYPE
	SYNTAX  Gauge32
	MAX-ACCESS  read-only
	STATUS  current
	DESCRIPTION
		"This counter gives the current rate at which JS is being sent in response to client requests."
	::= { serviceDospolicyEntry 8 }

svcdospolicydosTotValidClients  OBJECT-TYPE
	SYNTAX  Counter64
	MAX-ACCESS  read-only
	STATUS  current
	DESCRIPTION
		"This counter gives the total number of valid DOS cookies reveived for this policy."
	::= { serviceDospolicyEntry 9 }

svcdospolicydosCurServerRespRate  OBJECT-TYPE
	SYNTAX  Gauge32
	MAX-ACCESS  read-only
	STATUS  current
	DESCRIPTION
		"This counter gives the current rate at which the server to which this policy is bound is responding."
	::= { serviceDospolicyEntry 10 }

monitorMemberTable  OBJECT-TYPE
	SYNTAX  SEQUENCE OF MonitorMemberEntry
	MAX-ACCESS  not-accessible
	STATUS  current
	DESCRIPTION
		"The monitor table"
	::= { nsSvcGroup 9 }

monitorMemberEntry  OBJECT-TYPE
	SYNTAX  MonitorMemberEntry
	MAX-ACCESS  not-accessible
	STATUS  current
	DESCRIPTION
		"..."
	INDEX { monitorName   }
	::= { monitorMemberTable 1 }

MonitorMemberEntry ::= SEQUENCE {
	monitorName  OCTET STRING,
	responseTimeoutThreshold  Integer32,
	monitorType  MonitorType,
	monitorInterval  Integer32,
	monitorResponseTimeout  Integer32,
	monitorDowntime  Integer32,
	monitorRetrys  Integer32,
	destinationIP  IpAddress,
	destinationPort  Integer32,
	drtmDeviation  Integer32,
	drtmActiveMonitors  Integer32,
	drtmCumResponseTimeout  Gauge32,
	alarmProbeFailedRetries  Integer32,
	destinationInetAddressType  InetAddressType,
	destinationInetAddress  InetAddress
}

monitorName  OBJECT-TYPE
	SYNTAX  OCTET STRING
	MAX-ACCESS  read-only
	STATUS  current
	DESCRIPTION
		"Monitor name"
	::= { monitorMemberEntry 1 }

responseTimeoutThreshold  OBJECT-TYPE
	SYNTAX  Integer32
	MAX-ACCESS  read-only
	STATUS  current
	DESCRIPTION
		"Monitor Response timeout threshold, above which snmp trap will be fired.It is expressed in milliseconds."
	::= { monitorMemberEntry 2 }

monitorType  OBJECT-TYPE
	SYNTAX  MonitorType
	MAX-ACCESS  read-only
	STATUS  current
	DESCRIPTION
		"Type of the monitor."
	::= { monitorMemberEntry 3 }

monitorInterval  OBJECT-TYPE
	SYNTAX  Integer32
	MAX-ACCESS  read-only
	STATUS  current
	DESCRIPTION
		"Interval between monitoring probes.It is expressed in milliseconds."
	::= { monitorMemberEntry 4 }

monitorResponseTimeout  OBJECT-TYPE
	SYNTAX  Integer32
	MAX-ACCESS  read-only
	STATUS  current
	DESCRIPTION
		"Maximum time a monitor probe can take to respond.It is expressed in milliseconds."
	::= { monitorMemberEntry 5 }

monitorDowntime  OBJECT-TYPE
	SYNTAX  Integer32
	MAX-ACCESS  read-only
	STATUS  current
	DESCRIPTION
		"Time for which the monitor probes are not fired once it is down.It is expressed in milliseconds."
	::= { monitorMemberEntry 6 }

monitorRetrys  OBJECT-TYPE
	SYNTAX  Integer32
	MAX-ACCESS  read-only
	STATUS  current
	DESCRIPTION
		"Number of failed attempts to make server DOWN."
	::= { monitorMemberEntry 7 }

destinationIP  OBJECT-TYPE
	SYNTAX  IpAddress
	MAX-ACCESS  read-only
	STATUS  current
	DESCRIPTION
		"Destination IP address that is used for monitoring."
	::= { monitorMemberEntry 8 }

destinationPort  OBJECT-TYPE
	SYNTAX  Integer32
	MAX-ACCESS  read-only
	STATUS  current
	DESCRIPTION
		"Destination port that is used for monitoring."
	::= { monitorMemberEntry 9 }

drtmDeviation  OBJECT-TYPE
	SYNTAX  Integer32
	MAX-ACCESS  read-only
	STATUS  current
	DESCRIPTION
		"Tolerable Deviation of response time for DRTM.It is expressed in milliseconds."
	::= { monitorMemberEntry 10 }

drtmActiveMonitors  OBJECT-TYPE
	SYNTAX  Integer32
	MAX-ACCESS  read-only
	STATUS  current
	DESCRIPTION
		"Number of monitors contributing to DRTM average."
	::= { monitorMemberEntry 11 }

drtmCumResponseTimeout  OBJECT-TYPE
	SYNTAX  Gauge32
	MAX-ACCESS  read-only
	STATUS  current
	DESCRIPTION
		"Total cumulative response time of all active DRTM monitors.It is expressed in milliseconds."
	::= { monitorMemberEntry 12 }

alarmProbeFailedRetries  OBJECT-TYPE
	SYNTAX  Integer32
	MAX-ACCESS  read-only
	STATUS  current
	DESCRIPTION
		"Number of failed attempts to generate snmp trap."
	::= { monitorMemberEntry 13 }

destinationInetAddressType  OBJECT-TYPE
	SYNTAX  InetAddressType
	MAX-ACCESS  read-only
	STATUS  current
	DESCRIPTION
		"The address type of destinationInetAddress"
	::= { monitorMemberEntry 14 }

destinationInetAddress  OBJECT-TYPE
	SYNTAX  InetAddress
	MAX-ACCESS  read-only
	STATUS  current
	DESCRIPTION
		"Destination Internet address that is used for monitoring."
	::= { monitorMemberEntry 15 }

monServiceMemberTable  OBJECT-TYPE
	SYNTAX  SEQUENCE OF MonServiceMemberEntry
	MAX-ACCESS  not-accessible
	STATUS  current
	DESCRIPTION
		"The moninfo table, bindings of monitors to services."
	::= { nsSvcGroup 10 }

monServiceMemberEntry  OBJECT-TYPE
	SYNTAX  MonServiceMemberEntry
	MAX-ACCESS  not-accessible
	STATUS  current
	DESCRIPTION
		"..."
	INDEX { monServiceName , monitorName }
	::= { monServiceMemberTable 1 }

MonServiceMemberEntry ::= SEQUENCE {
	monServiceName  OCTET STRING,
	monitorRTO  Gauge32,
	monitorState  MonitorState,
	drtmRTO  Gauge32,
	drtmLearningProbes  Gauge32,
	monitorCurFailedCount  Gauge32,
	monitorWeight  Integer32,
	alarmMonrespto  Gauge32,
	monitorProbes  Counter32,
	monitorFailed  Counter32,
	monitorMaxClient  Counter32,
	monitorFailedCon  Counter32,
	monitorFailedCode  Counter32,
	monitorFailedStr  Counter32,
	monitorFailedTimeout  Counter32,
	monitorFailedSend  Counter32,
	monitorFailedFTP  Counter32,
	monitorFailedPort  Counter32,
	monitorFailedResponse  Counter32,
	monitorFailedId  Counter32,
	monitorProbesNoChange  Counter32,
	monitorResponseTimeoutThreshExceed  Counter32
}

monServiceName  OBJECT-TYPE
	SYNTAX  OCTET STRING
	MAX-ACCESS  read-only
	STATUS  current
	DESCRIPTION
		"The name of the service to which the monitor is bound."
	::= { monServiceMemberEntry 1 }

monitorRTO  OBJECT-TYPE
	SYNTAX  Gauge32
	MAX-ACCESS  read-only
	STATUS  current
	DESCRIPTION
		"Smooth response time calculated using LRTM. It is expressed in microseconds."
	::= { monServiceMemberEntry 2 }

monitorState  OBJECT-TYPE
	SYNTAX  MonitorState
	MAX-ACCESS  read-only
	STATUS  current
	DESCRIPTION
		"State of the monitor."
	::= { monServiceMemberEntry 3 }

drtmRTO  OBJECT-TYPE
	SYNTAX  Gauge32
	MAX-ACCESS  read-only
	STATUS  current
	DESCRIPTION
		"Monitor probe time (round trip time) for DRTM monitors.It is expressed in milliseconds."
	::= { monServiceMemberEntry 4 }

drtmLearningProbes  OBJECT-TYPE
	SYNTAX  Gauge32
	MAX-ACCESS  read-only
	STATUS  current
	DESCRIPTION
		"Current, number of monitoring probes yet to be done to move to dynamic mode in case of DRTM monitors."
	::= { monServiceMemberEntry 5 }

monitorCurFailedCount  OBJECT-TYPE
	SYNTAX  Gauge32
	MAX-ACCESS  read-only
	STATUS  current
	DESCRIPTION
		"Current, continuous monitoring probe failure count. gets reset on success only."
	::= { monServiceMemberEntry 6 }

monitorWeight  OBJECT-TYPE
	SYNTAX  Integer32
	MAX-ACCESS  read-only
	STATUS  current
	DESCRIPTION
		"Weight of the monitor binding."
	::= { monServiceMemberEntry 7 }

alarmMonrespto  OBJECT-TYPE
	SYNTAX  Gauge32
	MAX-ACCESS  accessible-for-notify
	STATUS  current
	DESCRIPTION
		"This is the response time taken for the current monitor probe."
	::= { monServiceMemberEntry 8 }

monitorProbes  OBJECT-TYPE
	SYNTAX  Counter32
	MAX-ACCESS  read-only
	STATUS  current
	DESCRIPTION
		"Number of monitoring probes sent."
	::= { monServiceMemberEntry 9 }

monitorFailed  OBJECT-TYPE
	SYNTAX  Counter32
	MAX-ACCESS  read-only
	STATUS  current
	DESCRIPTION
		"Number of monitoring probes failed."
	::= { monServiceMemberEntry 10 }

monitorMaxClient  OBJECT-TYPE
	SYNTAX  Counter32
	MAX-ACCESS  read-only
	STATUS  current
	DESCRIPTION
		"Number of monitoring probes that were not sent due to MaxClients."
	::= { monServiceMemberEntry 11 }

monitorFailedCon  OBJECT-TYPE
	SYNTAX  Counter32
	MAX-ACCESS  read-only
	STATUS  current
	DESCRIPTION
		"Number of failed monitoring probes due to failed connections."
	::= { monServiceMemberEntry 12 }

monitorFailedCode  OBJECT-TYPE
	SYNTAX  Counter32
	MAX-ACCESS  read-only
	STATUS  current
	DESCRIPTION
		"Number of failed monitoring probes due to improper response code."
	::= { monServiceMemberEntry 13 }

monitorFailedStr  OBJECT-TYPE
	SYNTAX  Counter32
	MAX-ACCESS  read-only
	STATUS  current
	DESCRIPTION
		"Number of failed monitoring probes due to invalid response string."
	::= { monServiceMemberEntry 14 }

monitorFailedTimeout  OBJECT-TYPE
	SYNTAX  Counter32
	MAX-ACCESS  read-only
	STATUS  current
	DESCRIPTION
		"Number of failed monitoring probes due to timeout."
	::= { monServiceMemberEntry 15 }

monitorFailedSend  OBJECT-TYPE
	SYNTAX  Counter32
	MAX-ACCESS  read-only
	STATUS  current
	DESCRIPTION
		"Number of failed monitoring probes due to inability to send the data."
	::= { monServiceMemberEntry 16 }

monitorFailedFTP  OBJECT-TYPE
	SYNTAX  Counter32
	MAX-ACCESS  read-only
	STATUS  current
	DESCRIPTION
		"Number of failed monitoring probes due to ftp protocol violation."
	::= { monServiceMemberEntry 17 }

monitorFailedPort  OBJECT-TYPE
	SYNTAX  Counter32
	MAX-ACCESS  read-only
	STATUS  current
	DESCRIPTION
		"Number of failed monitoring probes due to port unreachable response."
	::= { monServiceMemberEntry 18 }

monitorFailedResponse  OBJECT-TYPE
	SYNTAX  Counter32
	MAX-ACCESS  read-only
	STATUS  current
	DESCRIPTION
		"Number of failed monitoring probes due to invalid response."
	::= { monServiceMemberEntry 19 }

monitorFailedId  OBJECT-TYPE
	SYNTAX  Counter32
	MAX-ACCESS  read-only
	STATUS  current
	DESCRIPTION
		"Number of failed monitoring probes due to response id mismatch."
	::= { monServiceMemberEntry 20 }

monitorProbesNoChange  OBJECT-TYPE
	SYNTAX  Counter32
	MAX-ACCESS  read-only
	STATUS  current
	DESCRIPTION
		"Number of monitoring probes which did not change the state."
	::= { monServiceMemberEntry 21 }

monitorResponseTimeoutThreshExceed  OBJECT-TYPE
	SYNTAX  Counter32
	MAX-ACCESS  read-only
	STATUS  current
	DESCRIPTION
		" Number of times the response time has exceeded the configured threshold."
	::= { monServiceMemberEntry 22 }

serviceGroupTable  OBJECT-TYPE
	SYNTAX  SEQUENCE OF ServiceGroupEntry
	MAX-ACCESS  not-accessible
	STATUS  current
	DESCRIPTION
		"The netscaler services group table"
	::= { nsSvcGroup 11 }

serviceGroupEntry  OBJECT-TYPE
	SYNTAX  ServiceGroupEntry
	MAX-ACCESS  not-accessible
	STATUS  current
	DESCRIPTION
		"..."
	INDEX { svcgrpSvcGroupName   }
	::= { serviceGroupTable 1 }

ServiceGroupEntry ::= SEQUENCE {
	svcgrpSvcGroupName  OCTET STRING,
	svcgrpSvcGroupType  EntityProtocolType,
	svcgrpSvcGroupState  ServiceGroupState,
	svcgrpSvcGroupFullName  OCTET STRING
}

svcgrpSvcGroupName  OBJECT-TYPE
	SYNTAX  OCTET STRING
	MAX-ACCESS  read-only
	STATUS  current
	DESCRIPTION
		"The name of the service Group"
	::= { serviceGroupEntry 1 }

svcgrpSvcGroupType  OBJECT-TYPE
	SYNTAX  EntityProtocolType
	MAX-ACCESS  read-only
	STATUS  current
	DESCRIPTION
		"The type of the service Group."
	::= { serviceGroupEntry 2 }

svcgrpSvcGroupState  OBJECT-TYPE
	SYNTAX  ServiceGroupState
	MAX-ACCESS  read-only
	STATUS  current
	DESCRIPTION
		"The state of the service Group"
	::= { serviceGroupEntry 3 }

svcgrpSvcGroupFullName  OBJECT-TYPE
	SYNTAX  OCTET STRING
	MAX-ACCESS  read-only
	STATUS  current
	DESCRIPTION
		"The full name of the service Group"
	::= { serviceGroupEntry 4 }

nsVserverGroup OBJECT IDENTIFIER
	::= { rs9000 3 }

vserverTable  OBJECT-TYPE
	SYNTAX  SEQUENCE OF VserverEntry
	MAX-ACCESS  not-accessible
	STATUS  current
	DESCRIPTION
		"The vservers table"
	::= { nsVserverGroup 1 }

vserverEntry  OBJECT-TYPE
	SYNTAX  VserverEntry
	MAX-ACCESS  not-accessible
	STATUS  current
	DESCRIPTION
		"..."
	INDEX { vsvrName   }
	::= { vserverTable 1 }

VserverEntry ::= SEQUENCE {
	vsvrName  OCTET STRING,
	vsvrIpAddress  IpAddress,
	vsvrPort  Integer32,
	vsvrType  EntityProtocolType,
	vsvrState  EntityState,
	vsvrMaxReqPerConn  Counter32,
	vsvrCurClntConnections  Gauge32,
	vsvrCurSrvrConnections  Gauge32,
	vsvrAvgTransactionTime  TimeTicks,
	vsvrSurgeCount  Counter32,
	vsvrTotalRequestsLow  Counter32,
	vsvrTotalRequestsHigh  Counter32,
	vsvrTotalRequestBytesLow  Counter32,
	vsvrTotalRequestBytesHigh  Counter32,
	vsvrTotalResponsesLow  Counter32,
	vsvrTotalResponsesHigh  Counter32,
	vsvrTotalResponseBytesLow  Counter32,
	vsvrTotalResponseBytesHigh  Counter32,
	vsvrTotalPktsRecvdLow  Counter32,
	vsvrTotalPktsRecvdHigh  Counter32,
	vsvrTotalPktsSentLow  Counter32,
	vsvrTotalPktsSentHigh  Counter32,
	vsvrTotalSynsRecvdLow  Counter32,
	vsvrTotalSynsRecvdHigh  Counter32,
	vsvrTotalRequests  Counter64,
	vsvrTotalRequestBytes  Counter64,
	vsvrTotalResponses  Counter64,
	vsvrTotalResponseBytes  Counter64,
	vsvrTotalPktsRecvd  Counter64,
	vsvrTotalPktsSent  Counter64,
	vsvrTotalSynsRecvd  Counter64,
	vsvrCurServicesDown  Gauge32,
	vsvrCurServicesUnKnown  Gauge32,
	vsvrCurServicesOutOfSvc  Gauge32,
	vsvrCurServicesTransToOutOfSvc  Gauge32,
	vsvrCurServicesUp  Gauge32,
	vsvrTotMiss  Counter64,
	vsvrRequestRate  OCTET STRING,
	vsvrRxBytesRate  OCTET STRING,
	vsvrTxBytesRate  OCTET STRING,
	vsvrSynfloodRate  OCTET STRING,
	vsvrIp6Address  Ipv6Address,
	vsvrTotHits  Counter64,
	vsvrFullName  OCTET STRING,
	vsvrCurSslVpnUsers  Gauge32,
	vsvrTotalServicesBound  Gauge32,
	vsvrHealth  Integer32,
	vsvrTicksSinceLastStateChange  TimeTicks,
	vsvrTotSpillOvers  Counter32,
	vsvrEntityType  VServerType,
	vsvrTotalClients  Counter64,
	vsvrTotalServers  Counter64,
	vsvrClientConnOpenRate  OCTET STRING
}

vsvrName  OBJECT-TYPE
	SYNTAX  OCTET STRING
	MAX-ACCESS  read-only
	STATUS  current
	DESCRIPTION
		"The name of the vserver"
	::= { vserverEntry 1 }

vsvrIpAddress  OBJECT-TYPE
	SYNTAX  IpAddress
	MAX-ACCESS  read-only
	STATUS  current
	DESCRIPTION
		"IP address of the vserver"
	::= { vserverEntry 2 }

vsvrPort  OBJECT-TYPE
	SYNTAX  Integer32
	MAX-ACCESS  read-only
	STATUS  current
	DESCRIPTION
		"the port of the vserver"
	::= { vserverEntry 3 }

vsvrType  OBJECT-TYPE
	SYNTAX  EntityProtocolType
	MAX-ACCESS  read-only
	STATUS  current
	DESCRIPTION
		"Protocol associated with the vserver"
	::= { vserverEntry 4 }

vsvrState  OBJECT-TYPE
	SYNTAX  EntityState
	MAX-ACCESS  read-only
	STATUS  current
	DESCRIPTION
		"Current state of the server."
	::= { vserverEntry 5 }

vsvrMaxReqPerConn  OBJECT-TYPE
	SYNTAX  Counter32
	MAX-ACCESS  read-only
	STATUS  obsolete
	DESCRIPTION
		"...OBSOLETE"
	::= { vserverEntry 6 }

vsvrCurClntConnections  OBJECT-TYPE
	SYNTAX  Gauge32
	MAX-ACCESS  read-only
	STATUS  current
	DESCRIPTION
		"The number of current client connections."
	::= { vserverEntry 7 }

vsvrCurSrvrConnections  OBJECT-TYPE
	SYNTAX  Gauge32
	MAX-ACCESS  read-only
	STATUS  current
	DESCRIPTION
		"The number of current connections to the real servers behind the vserver."
	::= { vserverEntry 8 }

vsvrAvgTransactionTime  OBJECT-TYPE
	SYNTAX  TimeTicks
	MAX-ACCESS  read-only
	STATUS  obsolete
	DESCRIPTION
		"...OBSOLETE"
	::= { vserverEntry 9 }

vsvrSurgeCount  OBJECT-TYPE
	SYNTAX  Counter32
	MAX-ACCESS  read-only
	STATUS  current
	DESCRIPTION
		"The number requests in the surge queue."
	::= { vserverEntry 10 }

vsvrTotalRequestsLow  OBJECT-TYPE
	SYNTAX  Counter32
	MAX-ACCESS  read-only
	STATUS  obsolete
	DESCRIPTION
		"...OBSOLETE"
	::= { vserverEntry 11 }

vsvrTotalRequestsHigh  OBJECT-TYPE
	SYNTAX  Counter32
	MAX-ACCESS  read-only
	STATUS  obsolete
	DESCRIPTION
		"...OBSOLETE"
	::= { vserverEntry 12 }

vsvrTotalRequestBytesLow  OBJECT-TYPE
	SYNTAX  Counter32
	MAX-ACCESS  read-only
	STATUS  obsolete
	DESCRIPTION
		"...OBSOLETE"
	::= { vserverEntry 13 }

vsvrTotalRequestBytesHigh  OBJECT-TYPE
	SYNTAX  Counter32
	MAX-ACCESS  read-only
	STATUS  obsolete
	DESCRIPTION
		"...OBSOLETE"
	::= { vserverEntry 14 }

vsvrTotalResponsesLow  OBJECT-TYPE
	SYNTAX  Counter32
	MAX-ACCESS  read-only
	STATUS  obsolete
	DESCRIPTION
		"...OBSOLETE"
	::= { vserverEntry 15 }

vsvrTotalResponsesHigh  OBJECT-TYPE
	SYNTAX  Counter32
	MAX-ACCESS  read-only
	STATUS  obsolete
	DESCRIPTION
		"...OBSOLETE"
	::= { vserverEntry 16 }

vsvrTotalResponseBytesLow  OBJECT-TYPE
	SYNTAX  Counter32
	MAX-ACCESS  read-only
	STATUS  obsolete
	DESCRIPTION
		"...OBSOLETE"
	::= { vserverEntry 17 }

vsvrTotalResponseBytesHigh  OBJECT-TYPE
	SYNTAX  Counter32
	MAX-ACCESS  read-only
	STATUS  obsolete
	DESCRIPTION
		"...OBSOLETE"
	::= { vserverEntry 18 }

vsvrTotalPktsRecvdLow  OBJECT-TYPE
	SYNTAX  Counter32
	MAX-ACCESS  read-only
	STATUS  obsolete
	DESCRIPTION
		"...OBSOLETE"
	::= { vserverEntry 19 }

vsvrTotalPktsRecvdHigh  OBJECT-TYPE
	SYNTAX  Counter32
	MAX-ACCESS  read-only
	STATUS  obsolete
	DESCRIPTION
		"...OBSOLETE"
	::= { vserverEntry 20 }

vsvrTotalPktsSentLow  OBJECT-TYPE
	SYNTAX  Counter32
	MAX-ACCESS  read-only
	STATUS  obsolete
	DESCRIPTION
		"...OBSOLETE"
	::= { vserverEntry 21 }

vsvrTotalPktsSentHigh  OBJECT-TYPE
	SYNTAX  Counter32
	MAX-ACCESS  read-only
	STATUS  obsolete
	DESCRIPTION
		"...OBSOLETE"
	::= { vserverEntry 22 }

vsvrTotalSynsRecvdLow  OBJECT-TYPE
	SYNTAX  Counter32
	MAX-ACCESS  read-only
	STATUS  obsolete
	DESCRIPTION
		"...OBSOLETE"
	::= { vserverEntry 23 }

vsvrTotalSynsRecvdHigh  OBJECT-TYPE
	SYNTAX  Counter32
	MAX-ACCESS  read-only
	STATUS  obsolete
	DESCRIPTION
		"...OBSOLETE"
	::= { vserverEntry 24 }

vsvrTotalRequests  OBJECT-TYPE
	SYNTAX  Counter64
	MAX-ACCESS  read-only
	STATUS  current
	DESCRIPTION
		"The total number of requests received on this service/vserver(This is applicable for HTTP/SSL servicetype)."
	::= { vserverEntry 30 }

vsvrTotalRequestBytes  OBJECT-TYPE
	SYNTAX  Counter64
	MAX-ACCESS  read-only
	STATUS  current
	DESCRIPTION
		"The total number of request bytes received on this service/vserver."
	::= { vserverEntry 31 }

vsvrTotalResponses  OBJECT-TYPE
	SYNTAX  Counter64
	MAX-ACCESS  read-only
	STATUS  current
	DESCRIPTION
		"Number of responses received on this service/vserver(This is applicable for HTTP/SSL servicetype)."
	::= { vserverEntry 32 }

vsvrTotalResponseBytes  OBJECT-TYPE
	SYNTAX  Counter64
	MAX-ACCESS  read-only
	STATUS  current
	DESCRIPTION
		"Number of response bytes received on this service/vserver."
	::= { vserverEntry 33 }

vsvrTotalPktsRecvd  OBJECT-TYPE
	SYNTAX  Counter64
	MAX-ACCESS  read-only
	STATUS  current
	DESCRIPTION
		"The total number of packets received on this service/vserver."
	::= { vserverEntry 34 }

vsvrTotalPktsSent  OBJECT-TYPE
	SYNTAX  Counter64
	MAX-ACCESS  read-only
	STATUS  current
	DESCRIPTION
		"  The total number of packets sent. "
	::= { vserverEntry 35 }

vsvrTotalSynsRecvd  OBJECT-TYPE
	SYNTAX  Counter64
	MAX-ACCESS  read-only
	STATUS  current
	DESCRIPTION
		"The total number of syns received from clients on this service/vserver."
	::= { vserverEntry 36 }

vsvrCurServicesDown  OBJECT-TYPE
	SYNTAX  Gauge32
	MAX-ACCESS  read-only
	STATUS  current
	DESCRIPTION
		"The current number of services which are bound to this vserver and are in the state 'down'."
	::= { vserverEntry 37 }

vsvrCurServicesUnKnown  OBJECT-TYPE
	SYNTAX  Gauge32
	MAX-ACCESS  read-only
	STATUS  current
	DESCRIPTION
		"The current number of services which are bound to this vserver and are in the state 'unKnown'."
	::= { vserverEntry 38 }

vsvrCurServicesOutOfSvc  OBJECT-TYPE
	SYNTAX  Gauge32
	MAX-ACCESS  read-only
	STATUS  current
	DESCRIPTION
		"The current number of services which are bound to this vserver and are in the state 'outOfService'."
	::= { vserverEntry 39 }

vsvrCurServicesTransToOutOfSvc  OBJECT-TYPE
	SYNTAX  Gauge32
	MAX-ACCESS  read-only
	STATUS  current
	DESCRIPTION
		"The current number of services which are bound to this vserver and are in the state 'transitionToOutOfService'."
	::= { vserverEntry 40 }

vsvrCurServicesUp  OBJECT-TYPE
	SYNTAX  Gauge32
	MAX-ACCESS  read-only
	STATUS  current
	DESCRIPTION
		"The current number of services which are bound to this vserver and are in the state 'up'."
	::= { vserverEntry 41 }

vsvrTotMiss  OBJECT-TYPE
	SYNTAX  Counter64
	MAX-ACCESS  read-only
	STATUS  current
	DESCRIPTION
		"Total vserver misses"
	::= { vserverEntry 42 }

vsvrRequestRate  OBJECT-TYPE
	SYNTAX  OCTET STRING
	MAX-ACCESS  read-only
	STATUS  current
	DESCRIPTION
		"This represents the request rate in requests per second for this service/vserver."
	::= { vserverEntry 43 }

vsvrRxBytesRate  OBJECT-TYPE
	SYNTAX  OCTET STRING
	MAX-ACCESS  read-only
	STATUS  current
	DESCRIPTION
		"This represents the request rate in bytes per second fot this service/vserver."
	::= { vserverEntry 44 }

vsvrTxBytesRate  OBJECT-TYPE
	SYNTAX  OCTET STRING
	MAX-ACCESS  read-only
	STATUS  current
	DESCRIPTION
		"This represents the response rate in bytes per second fot this service/vserver."
	::= { vserverEntry 45 }

vsvrSynfloodRate  OBJECT-TYPE
	SYNTAX  OCTET STRING
	MAX-ACCESS  read-only
	STATUS  current
	DESCRIPTION
		"This represents the rate of unacknowledged SYNs for this service/vserver."
	::= { vserverEntry 46 }

vsvrIp6Address  OBJECT-TYPE
	SYNTAX  Ipv6Address
	MAX-ACCESS  read-only
	STATUS  current
	DESCRIPTION
		"IPv6 address of the v server"
	::= { vserverEntry 47 }

vsvrTotHits  OBJECT-TYPE
	SYNTAX  Counter64
	MAX-ACCESS  read-only
	STATUS  current
	DESCRIPTION
		"Total vserver hits"
	::= { vserverEntry 48 }

vsvrFullName  OBJECT-TYPE
	SYNTAX  OCTET STRING
	MAX-ACCESS  read-only
	STATUS  current
	DESCRIPTION
		"The name of the vserver"
	::= { vserverEntry 49 }

vsvrCurSslVpnUsers  OBJECT-TYPE
	SYNTAX  Gauge32
	MAX-ACCESS  read-only
	STATUS  current
	DESCRIPTION
		"The current number of ssl users accessing this VIP."
	::= { vserverEntry 50 }

vsvrTotalServicesBound  OBJECT-TYPE
	SYNTAX  Gauge32
	MAX-ACCESS  read-only
	STATUS  current
	DESCRIPTION
		"The current number of services which are bound to this vserver."
	::= { vserverEntry 51 }

vsvrHealth  OBJECT-TYPE
	SYNTAX  Integer32
	MAX-ACCESS  read-only
	STATUS  current
	DESCRIPTION
		"The percentage of UP services bound to this vserver."
	::= { vserverEntry 52 }

vsvrTicksSinceLastStateChange  OBJECT-TYPE
	SYNTAX  TimeTicks
	MAX-ACCESS  read-only
	STATUS  current
	DESCRIPTION
		"Time (in 10 milliseconds) since the last state change."
	::= { vserverEntry 53 }

vsvrTotSpillOvers  OBJECT-TYPE
	SYNTAX  Counter32
	MAX-ACCESS  read-only
	STATUS  current
	DESCRIPTION
		"Number of times vserver expereinced spill over."
	::= { vserverEntry 54 }

vsvrEntityType  OBJECT-TYPE
	SYNTAX  VServerType
	MAX-ACCESS  read-only
	STATUS  current
	DESCRIPTION
		"The type of the vserver."
	::= { vserverEntry 55 }

vsvrTotalClients  OBJECT-TYPE
	SYNTAX  Counter64
	MAX-ACCESS  read-only
	STATUS  current
	DESCRIPTION
		"The total number of established client connections."
	::= { vserverEntry 56 }

vsvrTotalServers  OBJECT-TYPE
	SYNTAX  Counter64
	MAX-ACCESS  read-only
	STATUS  current
	DESCRIPTION
		"The total number of established server connections."
	::= { vserverEntry 57 }

vsvrClientConnOpenRate  OBJECT-TYPE
	SYNTAX  OCTET STRING
	MAX-ACCESS  read-only
	STATUS  current
	DESCRIPTION
		"Rate at which connections are opened for this vserver."
	::= { vserverEntry 58 }

vserverServiceTable  OBJECT-TYPE
	SYNTAX  SEQUENCE OF VserverServiceEntry
	MAX-ACCESS  not-accessible
	STATUS  current
	DESCRIPTION
		"The vserver service relationship table"
	::= { nsVserverGroup 2 }

vserverServiceEntry  OBJECT-TYPE
	SYNTAX  VserverServiceEntry
	MAX-ACCESS  not-accessible
	STATUS  current
	DESCRIPTION
		"..."
	INDEX { vsvrName , vsvrServiceName }
	::= { vserverServiceTable 1 }

VserverServiceEntry ::= SEQUENCE {
	serviceHitsLow  Counter32,
	serviceHitsHigh  Counter32,
	servicePersistentHitsLow  Counter32,
	servicePersistentHitsHigh  Counter32,
	vsvrServiceHits  Counter64,
	servicePersistentHits  Counter64,
	serviceWeight  Integer32,
	vsvrServiceName  OCTET STRING,
	vsvrServiceFullName  OCTET STRING,
	vserverFullName  OCTET STRING,
	vsvrServiceEntityType  SvcEntityType
}

serviceHitsLow  OBJECT-TYPE
	SYNTAX  Counter32
	MAX-ACCESS  read-only
	STATUS  obsolete
	DESCRIPTION
		"...OBSOLETE"
	::= { vserverServiceEntry 1 }

serviceHitsHigh  OBJECT-TYPE
	SYNTAX  Counter32
	MAX-ACCESS  read-only
	STATUS  obsolete
	DESCRIPTION
		"...OBSOLETE"
	::= { vserverServiceEntry 2 }

servicePersistentHitsLow  OBJECT-TYPE
	SYNTAX  Counter32
	MAX-ACCESS  read-only
	STATUS  obsolete
	DESCRIPTION
		"...OBSOLETE"
	::= { vserverServiceEntry 3 }

servicePersistentHitsHigh  OBJECT-TYPE
	SYNTAX  Counter32
	MAX-ACCESS  read-only
	STATUS  obsolete
	DESCRIPTION
		"...OBSOLETE"
	::= { vserverServiceEntry 4 }

vsvrServiceHits  OBJECT-TYPE
	SYNTAX  Counter64
	MAX-ACCESS  read-only
	STATUS  current
	DESCRIPTION
		"This represents the number of times that the service has been provided."
	::= { vserverServiceEntry 5 }

servicePersistentHits  OBJECT-TYPE
	SYNTAX  Counter64
	MAX-ACCESS  read-only
	STATUS  current
	DESCRIPTION
		"The total number of persistent hits."
	::= { vserverServiceEntry 6 }

serviceWeight  OBJECT-TYPE
	SYNTAX  Integer32
	MAX-ACCESS  read-write
	STATUS  current
	DESCRIPTION
		"The weight of the service tied to the vserver."
	::= { vserverServiceEntry 7 }

vsvrServiceName  OBJECT-TYPE
	SYNTAX  OCTET STRING
	MAX-ACCESS  read-only
	STATUS  current
	DESCRIPTION
		"The name of the service to which the vserver is bound."
	::= { vserverServiceEntry 8 }

vsvrServiceFullName  OBJECT-TYPE
	SYNTAX  OCTET STRING
	MAX-ACCESS  read-only
	STATUS  current
	DESCRIPTION
		"The Full name of the service to which the vserver is bound."
	::= { vserverServiceEntry 9 }

vserverFullName  OBJECT-TYPE
	SYNTAX  OCTET STRING
	MAX-ACCESS  read-only
	STATUS  current
	DESCRIPTION
		"The full name of the vserver."
	::= { vserverServiceEntry 10 }

vsvrServiceEntityType  OBJECT-TYPE
	SYNTAX  SvcEntityType
	MAX-ACCESS  read-only
	STATUS  current
	DESCRIPTION
		"The entity type of the service: service group member or service."
	::= { vserverServiceEntry 11 }

vserverCspolicyTable  OBJECT-TYPE
	SYNTAX  SEQUENCE OF VserverCspolicyEntry
	MAX-ACCESS  not-accessible
	STATUS  current
	DESCRIPTION
		"The vserver content switching policy relationship table"
	::= { nsVserverGroup 3 }

vserverCspolicyEntry  OBJECT-TYPE
	SYNTAX  VserverCspolicyEntry
	MAX-ACCESS  not-accessible
	STATUS  current
	DESCRIPTION
		"..."
	INDEX { vsvrName , cspolicyName }
	::= { vserverCspolicyTable 1 }

VserverCspolicyEntry ::= SEQUENCE {
	cspolicyName  OCTET STRING,
	cspolicyDestVserverName  OCTET STRING,
	cspolicyHitsLow  Counter32,
	cspolicyHitsHigh  Counter32,
	cspolicyHits  Counter64,
	csIndexVserverFullName  OCTET STRING
}

cspolicyName  OBJECT-TYPE
	SYNTAX  OCTET STRING
	MAX-ACCESS  read-only
	STATUS  current
	DESCRIPTION
		"This represents the name of the policy bound to content switching vserver "
	::= { vserverCspolicyEntry 1 }

cspolicyDestVserverName  OBJECT-TYPE
	SYNTAX  OCTET STRING
	MAX-ACCESS  read-only
	STATUS  current
	DESCRIPTION
		"This represents the name of the destination vserver to which the request has to be directed to if the content switching policy evaluates to true."
	::= { vserverCspolicyEntry 2 }

cspolicyHitsLow  OBJECT-TYPE
	SYNTAX  Counter32
	MAX-ACCESS  read-only
	STATUS  obsolete
	DESCRIPTION
		"...OBSOLETE"
	::= { vserverCspolicyEntry 3 }

cspolicyHitsHigh  OBJECT-TYPE
	SYNTAX  Counter32
	MAX-ACCESS  read-only
	STATUS  obsolete
	DESCRIPTION
		"...OBSOLETE"
	::= { vserverCspolicyEntry 4 }

cspolicyHits  OBJECT-TYPE
	SYNTAX  Counter64
	MAX-ACCESS  read-only
	STATUS  current
	DESCRIPTION
		"This represents the number of hits on this policy."
	::= { vserverCspolicyEntry 5 }

csIndexVserverFullName  OBJECT-TYPE
	SYNTAX  OCTET STRING
	MAX-ACCESS  read-only
	STATUS  current
	DESCRIPTION
		"The full name of the cs vserver to which this policy belongs."
	::= { vserverCspolicyEntry 6 }

vserverCrpolicyTable  OBJECT-TYPE
	SYNTAX  SEQUENCE OF VserverCrpolicyEntry
	MAX-ACCESS  not-accessible
	STATUS  current
	DESCRIPTION
		"The vserver cache redirection policy relationship table"
	::= { nsVserverGroup 4 }

vserverCrpolicyEntry  OBJECT-TYPE
	SYNTAX  VserverCrpolicyEntry
	MAX-ACCESS  not-accessible
	STATUS  current
	DESCRIPTION
		"..."
	INDEX { vsvrName , crpolicyName }
	::= { vserverCrpolicyTable 1 }

VserverCrpolicyEntry ::= SEQUENCE {
	crpolicyName  OCTET STRING,
	crpolicyHitsLow  Counter32,
	crpolicyHitsHigh  Counter32,
	crpolicyHits  Counter64,
	crIndexVserverFullName  OCTET STRING
}

crpolicyName  OBJECT-TYPE
	SYNTAX  OCTET STRING
	MAX-ACCESS  read-only
	STATUS  current
	DESCRIPTION
		"This represents the name of the policy bound to cache-redirection vserver "
	::= { vserverCrpolicyEntry 1 }

crpolicyHitsLow  OBJECT-TYPE
	SYNTAX  Counter32
	MAX-ACCESS  read-only
	STATUS  obsolete
	DESCRIPTION
		"...OBSOLETE"
	::= { vserverCrpolicyEntry 2 }

crpolicyHitsHigh  OBJECT-TYPE
	SYNTAX  Counter32
	MAX-ACCESS  read-only
	STATUS  obsolete
	DESCRIPTION
		"...OBSOLETE"
	::= { vserverCrpolicyEntry 3 }

crpolicyHits  OBJECT-TYPE
	SYNTAX  Counter64
	MAX-ACCESS  read-only
	STATUS  current
	DESCRIPTION
		"This represents the hits on the cr policy. "
	::= { vserverCrpolicyEntry 4 }

crIndexVserverFullName  OBJECT-TYPE
	SYNTAX  OCTET STRING
	MAX-ACCESS  read-only
	STATUS  current
	DESCRIPTION
		"The full name of the cr vserver to which this policy belongs."
	::= { vserverCrpolicyEntry 5 }

vserverGlobalStatsGroup OBJECT IDENTIFIER
	::= { nsVserverGroup 5 }

curConfigVservers  OBJECT-TYPE
	SYNTAX  Gauge32
	MAX-ACCESS  read-only
	STATUS  current
	DESCRIPTION
		"Total number of vservers configured on the NetScaler."
	::= { vserverGlobalStatsGroup 1 }

vsvrBindCount  OBJECT-TYPE
	SYNTAX  Integer32
	MAX-ACCESS  read-only
	STATUS  current
	DESCRIPTION
		"Number of vserver bindings in the system"
	::= { vserverGlobalStatsGroup 2 }

vsvrSvcGrpBindCount  OBJECT-TYPE
	SYNTAX  Integer32
	MAX-ACCESS  read-only
	STATUS  current
	DESCRIPTION
		"Number of vserver, servicegroup bindings in the system"
	::= { vserverGlobalStatsGroup 3 }

lbvserverTable  OBJECT-TYPE
	SYNTAX  SEQUENCE OF LbvserverEntry
	MAX-ACCESS  not-accessible
	STATUS  current
	DESCRIPTION
		"Table for LB specific configuration"
	::= { nsVserverGroup 6 }

lbvserverEntry  OBJECT-TYPE
	SYNTAX  LbvserverEntry
	MAX-ACCESS  not-accessible
	STATUS  current
	DESCRIPTION
		"..."
	INDEX { vsvrName   }
	::= { lbvserverTable 1 }

LbvserverEntry ::= SEQUENCE {
	lbvsvrLBMethod  LbPolicy,
	lbvsvrPersistanceType  PersistanceType,
	lbvsvrPersistenceTimeOut  Integer32,
	lbvsvrActiveConn  Gauge32,
	lbvsvrAvgSvrTTFB  Gauge32
}

lbvsvrLBMethod  OBJECT-TYPE
	SYNTAX  LbPolicy
	MAX-ACCESS  read-only
	STATUS  current
	DESCRIPTION
		"The Policy used for Load Balancing."
	::= { lbvserverEntry 1 }

lbvsvrPersistanceType  OBJECT-TYPE
	SYNTAX  PersistanceType
	MAX-ACCESS  read-only
	STATUS  current
	DESCRIPTION
		"The type of persistence used."
	::= { lbvserverEntry 2 }

lbvsvrPersistenceTimeOut  OBJECT-TYPE
	SYNTAX  Integer32
	MAX-ACCESS  read-only
	STATUS  current
	DESCRIPTION
		"The timeout set for persistence."
	::= { lbvserverEntry 3 }

lbvsvrActiveConn  OBJECT-TYPE
	SYNTAX  Gauge32
	MAX-ACCESS  read-only
	STATUS  current
	DESCRIPTION
		"The number of established connections that are currently active. "
	::= { lbvserverEntry 4 }

lbvsvrAvgSvrTTFB  OBJECT-TYPE
	SYNTAX  Gauge32
	MAX-ACCESS  read-only
	STATUS  current
	DESCRIPTION
		"The average TTFB between the netscaler and the server."
	::= { lbvserverEntry 5 }

vserverPqpolicyTable  OBJECT-TYPE
	SYNTAX  SEQUENCE OF VserverPqpolicyEntry
	MAX-ACCESS  not-accessible
	STATUS  current
	DESCRIPTION
		"The vserver priority queuing policy relationship table"
	::= { nsVserverGroup 7 }

vserverPqpolicyEntry  OBJECT-TYPE
	SYNTAX  VserverPqpolicyEntry
	MAX-ACCESS  not-accessible
	STATUS  current
	DESCRIPTION
		"..."
	INDEX { vsvrName , pqName }
	::= { vserverPqpolicyTable 1 }

VserverPqpolicyEntry ::= SEQUENCE {
	pqpolicyTotClientTransactionTime  Counter64,
	pqpolicyTotClientTransactions  Counter64,
	pqpolicyDropped  Counter64,
	pqpolicyQdepth  Counter32,
	pqpolicytotClientTransactionTime  Counter64,
	pqpolicytotClientTransactions  Counter64,
	pqpolicypqDropped  Counter64,
	pqpolicypqQdepth  Gauge32,
	pqpolicypqAvgClientTransactionTime  Gauge32,
	pqpolicypqVserverIP  IpAddress,
	pqpolicypqVserverPort  Integer32,
	pqpolicypqCurrentClientConnections  Gauge32,
	pqpolicypqTotQueueDepth  Counter64,
	pqpolicypqTotClientConnections  Counter64,
	pqpolicypqTotQueueWaitTime  Counter64,
	pqpolicypqTotAvgQueueDepth  Gauge32,
	pqpolicypqTotAvgQueueWaitTime  Gauge32,
	pqpolicytotClientTransactionTimems  Counter64,
	pqpolicypqAvgClientTransactionTimems  Gauge32
}

pqpolicyTotClientTransactionTime  OBJECT-TYPE
	SYNTAX  Counter64
	MAX-ACCESS  read-only
	STATUS  obsolete
	DESCRIPTION
		"...OBSOLETE"
	::= { vserverPqpolicyEntry 1 }

pqpolicyTotClientTransactions  OBJECT-TYPE
	SYNTAX  Counter64
	MAX-ACCESS  read-only
	STATUS  obsolete
	DESCRIPTION
		"...OBSOLETE"
	::= { vserverPqpolicyEntry 2 }

pqpolicyDropped  OBJECT-TYPE
	SYNTAX  Counter64
	MAX-ACCESS  read-only
	STATUS  obsolete
	DESCRIPTION
		"...OBSOLETE"
	::= { vserverPqpolicyEntry 3 }

pqpolicyQdepth  OBJECT-TYPE
	SYNTAX  Counter32
	MAX-ACCESS  read-only
	STATUS  obsolete
	DESCRIPTION
		"...OBSOLETE"
	::= { vserverPqpolicyEntry 4 }

pqpolicytotClientTransactionTime  OBJECT-TYPE
	SYNTAX  Counter64
	MAX-ACCESS  read-only
	STATUS  current
	DESCRIPTION
		"Total client transaction time in microsec. "
	::= { vserverPqpolicyEntry 5 }

pqpolicytotClientTransactions  OBJECT-TYPE
	SYNTAX  Counter64
	MAX-ACCESS  read-only
	STATUS  current
	DESCRIPTION
		"Total number of client transactions."
	::= { vserverPqpolicyEntry 6 }

pqpolicypqDropped  OBJECT-TYPE
	SYNTAX  Counter64
	MAX-ACCESS  read-only
	STATUS  current
	DESCRIPTION
		"Number of dropped transactions."
	::= { vserverPqpolicyEntry 7 }

pqpolicypqQdepth  OBJECT-TYPE
	SYNTAX  Gauge32
	MAX-ACCESS  read-only
	STATUS  current
	DESCRIPTION
		"Number of waiting clients. "
	::= { vserverPqpolicyEntry 8 }

pqpolicypqAvgClientTransactionTime  OBJECT-TYPE
	SYNTAX  Gauge32
	MAX-ACCESS  read-only
	STATUS  current
	DESCRIPTION
		"This counter gives the average time taken by a PQ client to complete its transaction."
	::= { vserverPqpolicyEntry 9 }

pqpolicypqVserverIP  OBJECT-TYPE
	SYNTAX  IpAddress
	MAX-ACCESS  read-only
	STATUS  current
	DESCRIPTION
		"Gives the IP address of the vserver to which this policy is bound."
	::= { vserverPqpolicyEntry 10 }

pqpolicypqVserverPort  OBJECT-TYPE
	SYNTAX  Integer32
	MAX-ACCESS  read-only
	STATUS  current
	DESCRIPTION
		"Gives the port of the vserver to which this policy is bound."
	::= { vserverPqpolicyEntry 11 }

pqpolicypqCurrentClientConnections  OBJECT-TYPE
	SYNTAX  Gauge32
	MAX-ACCESS  read-only
	STATUS  current
	DESCRIPTION
		"This counter gives the current number of server connections established for this policy."
	::= { vserverPqpolicyEntry 12 }

pqpolicypqTotQueueDepth  OBJECT-TYPE
	SYNTAX  Counter64
	MAX-ACCESS  read-only
	STATUS  current
	DESCRIPTION
		"This counter gives the total queue depth for this policy."
	::= { vserverPqpolicyEntry 13 }

pqpolicypqTotClientConnections  OBJECT-TYPE
	SYNTAX  Counter64
	MAX-ACCESS  read-only
	STATUS  current
	DESCRIPTION
		"This counter gives the total number of server connections established for this policy."
	::= { vserverPqpolicyEntry 14 }

pqpolicypqTotQueueWaitTime  OBJECT-TYPE
	SYNTAX  Counter64
	MAX-ACCESS  read-only
	STATUS  current
	DESCRIPTION
		"This counter gives the amount of time spent by PQ clients in the priority queue."
	::= { vserverPqpolicyEntry 15 }

pqpolicypqTotAvgQueueDepth  OBJECT-TYPE
	SYNTAX  Gauge32
	MAX-ACCESS  read-only
	STATUS  current
	DESCRIPTION
		"This counter gives the average queue depth for this priority queue policy."
	::= { vserverPqpolicyEntry 16 }

pqpolicypqTotAvgQueueWaitTime  OBJECT-TYPE
	SYNTAX  Gauge32
	MAX-ACCESS  read-only
	STATUS  current
	DESCRIPTION
		"This counter gives the average waiting time for this priority queue policy."
	::= { vserverPqpolicyEntry 17 }

pqpolicytotClientTransactionTimems  OBJECT-TYPE
	SYNTAX  Counter64
	MAX-ACCESS  read-only
	STATUS  current
	DESCRIPTION
		"Total client transaction time in microsec. "
	::= { vserverPqpolicyEntry 18 }

pqpolicypqAvgClientTransactionTimems  OBJECT-TYPE
	SYNTAX  Gauge32
	MAX-ACCESS  read-only
	STATUS  current
	DESCRIPTION
		"This counter gives the average time taken by a PQ client to complete its transaction."
	::= { vserverPqpolicyEntry 19 }

vserverScpolicyTable  OBJECT-TYPE
	SYNTAX  SEQUENCE OF VserverScpolicyEntry
	MAX-ACCESS  not-accessible
	STATUS  current
	DESCRIPTION
		"The vserver sure connect policy relationship table"
	::= { nsVserverGroup 8 }

vserverScpolicyEntry  OBJECT-TYPE
	SYNTAX  VserverScpolicyEntry
	MAX-ACCESS  not-accessible
	STATUS  current
	DESCRIPTION
		"..."
	INDEX { svcServiceName , scPolicyName }
	::= { vserverScpolicyTable 1 }

VserverScpolicyEntry ::= SEQUENCE {
	vsvrscpolicyPrimaryIPAddress  IpAddress,
	vsvrscpolicyPrimaryPort  Integer32,
	vsvrscpolicyDesIpAddress  IpAddress,
	vsvrscpolicyDestPort  Integer32,
	vsvrscpolicyAvgServerTransactionTime  Gauge32,
	vsvrscpolicyTotClientTransaction  Counter64,
	vsvrscpolicyTotOpenConn  Counter32,
	vsvrscpolicydesIpAddress  IpAddress,
	vsvrscpolicydestPort  Integer32,
	vsvrscpolicyavgServerTransactionTime  Gauge32,
	vsvrscpolicytotClientTransaction  Counter64,
	vsvrscpolicytotOpenConn  Gauge32,
	vsvrscpolicyscPhysicalServiceIP  IpAddress,
	vsvrscpolicyscPhysicalServicePort  Integer32,
	vsvrscpolicyscCurrentWaitingTime  Gauge32,
	vsvrscpolicyscCurrentClientConnections  Gauge32,
	vsvrscpolicyscTotalClientConnections  Counter64,
	vsvrscpolicyscTotalServerConnections  Counter64,
	vsvrscpolicyscTotalRequestsReceived  Counter64,
	vsvrscpolicyscTotalRequestBytes  Counter64,
	vsvrscpolicyscTotalResponsesReceived  Counter64,
	vsvrscpolicyscTotalResponseBytes  Counter64,
	vsvrscpolicyscCurrentSurgeQClients  Gauge32,
	vsvrscpolicyscCurrentWaitingClients  Gauge32,
	vsvrscpolicyscTotalServerTransactions  Counter64,
	vsvrscpolicyscTotalServerTTFBTransactions  Counter64,
	vsvrscpolicyscTotalServerTTLB  Counter64,
	vsvrscpolicyscTotalClientTTLB  Counter64,
	vsvrscpolicyscTotalServerTTFB  Counter64,
	vsvrscpolicyscAverageClientTTLB  Gauge32,
	vsvrscpolicyscAverageServerTTFB  Gauge32
}

vsvrscpolicyPrimaryIPAddress  OBJECT-TYPE
	SYNTAX  IpAddress
	MAX-ACCESS  read-only
	STATUS  current
	DESCRIPTION
		"The ip address at which the service is running."
	::= { vserverScpolicyEntry 1 }

vsvrscpolicyPrimaryPort  OBJECT-TYPE
	SYNTAX  Integer32
	MAX-ACCESS  read-only
	STATUS  current
	DESCRIPTION
		"The port of the vserver/service to which the scpolicy is bound."
	::= { vserverScpolicyEntry 2 }

vsvrscpolicyDesIpAddress  OBJECT-TYPE
	SYNTAX  IpAddress
	MAX-ACCESS  read-only
	STATUS  obsolete
	DESCRIPTION
		"...OBSOLETE"
	::= { vserverScpolicyEntry 3 }

vsvrscpolicyDestPort  OBJECT-TYPE
	SYNTAX  Integer32
	MAX-ACCESS  read-only
	STATUS  obsolete
	DESCRIPTION
		"...OBSOLETE"
	::= { vserverScpolicyEntry 4 }

vsvrscpolicyAvgServerTransactionTime  OBJECT-TYPE
	SYNTAX  Gauge32
	MAX-ACCESS  read-only
	STATUS  obsolete
	DESCRIPTION
		"...OBSOLETE"
	::= { vserverScpolicyEntry 5 }

vsvrscpolicyTotClientTransaction  OBJECT-TYPE
	SYNTAX  Counter64
	MAX-ACCESS  read-only
	STATUS  obsolete
	DESCRIPTION
		"...OBSOLETE"
	::= { vserverScpolicyEntry 6 }

vsvrscpolicyTotOpenConn  OBJECT-TYPE
	SYNTAX  Counter32
	MAX-ACCESS  read-only
	STATUS  obsolete
	DESCRIPTION
		"...OBSOLETE"
	::= { vserverScpolicyEntry 7 }

vsvrscpolicydesIpAddress  OBJECT-TYPE
	SYNTAX  IpAddress
	MAX-ACCESS  read-only
	STATUS  current
	DESCRIPTION
		"IP address of destination physical service."
	::= { vserverScpolicyEntry 8 }

vsvrscpolicydestPort  OBJECT-TYPE
	SYNTAX  Integer32
	MAX-ACCESS  read-only
	STATUS  current
	DESCRIPTION
		"Port number of destination physical service."
	::= { vserverScpolicyEntry 9 }

vsvrscpolicyavgServerTransactionTime  OBJECT-TYPE
	SYNTAX  Gauge32
	MAX-ACCESS  read-only
	STATUS  current
	DESCRIPTION
		"Average Server transaction time."
	::= { vserverScpolicyEntry 10 }

vsvrscpolicytotClientTransaction  OBJECT-TYPE
	SYNTAX  Counter64
	MAX-ACCESS  read-only
	STATUS  current
	DESCRIPTION
		"Total number of client transactions for this policy."
	::= { vserverScpolicyEntry 11 }

vsvrscpolicytotOpenConn  OBJECT-TYPE
	SYNTAX  Gauge32
	MAX-ACCESS  read-only
	STATUS  current
	DESCRIPTION
		"Total number of open connections for this policy."
	::= { vserverScpolicyEntry 12 }

vsvrscpolicyscPhysicalServiceIP  OBJECT-TYPE
	SYNTAX  IpAddress
	MAX-ACCESS  read-only
	STATUS  current
	DESCRIPTION
		"The IP address of the physical service for which this statistics is maintained."
	::= { vserverScpolicyEntry 13 }

vsvrscpolicyscPhysicalServicePort  OBJECT-TYPE
	SYNTAX  Integer32
	MAX-ACCESS  read-only
	STATUS  current
	DESCRIPTION
		"The port of the physical service for which this statistics is maintained."
	::= { vserverScpolicyEntry 14 }

vsvrscpolicyscCurrentWaitingTime  OBJECT-TYPE
	SYNTAX  Gauge32
	MAX-ACCESS  read-only
	STATUS  current
	DESCRIPTION
		"This counter gives the value of the currently estimated waiting time for the configured URL."
	::= { vserverScpolicyEntry 15 }

vsvrscpolicyscCurrentClientConnections  OBJECT-TYPE
	SYNTAX  Gauge32
	MAX-ACCESS  read-only
	STATUS  current
	DESCRIPTION
		"This counter gives the number of clients that were allowed a server connection for this policy."
	::= { vserverScpolicyEntry 16 }

vsvrscpolicyscTotalClientConnections  OBJECT-TYPE
	SYNTAX  Counter64
	MAX-ACCESS  read-only
	STATUS  current
	DESCRIPTION
		"This counter gives the total number of clients that were allowed a server connection for this policy."
	::= { vserverScpolicyEntry 17 }

vsvrscpolicyscTotalServerConnections  OBJECT-TYPE
	SYNTAX  Counter64
	MAX-ACCESS  read-only
	STATUS  current
	DESCRIPTION
		"This counter gives the total number of server connections that were established for this policy."
	::= { vserverScpolicyEntry 18 }

vsvrscpolicyscTotalRequestsReceived  OBJECT-TYPE
	SYNTAX  Counter64
	MAX-ACCESS  read-only
	STATUS  current
	DESCRIPTION
		"This counter gives the total number of requests received for this policy."
	::= { vserverScpolicyEntry 19 }

vsvrscpolicyscTotalRequestBytes  OBJECT-TYPE
	SYNTAX  Counter64
	MAX-ACCESS  read-only
	STATUS  current
	DESCRIPTION
		"This counter gives the total number of request bytes received for this policy."
	::= { vserverScpolicyEntry 20 }

vsvrscpolicyscTotalResponsesReceived  OBJECT-TYPE
	SYNTAX  Counter64
	MAX-ACCESS  read-only
	STATUS  current
	DESCRIPTION
		"This counter gives the total number of server responses received for this policy."
	::= { vserverScpolicyEntry 21 }

vsvrscpolicyscTotalResponseBytes  OBJECT-TYPE
	SYNTAX  Counter64
	MAX-ACCESS  read-only
	STATUS  current
	DESCRIPTION
		"This counter gives the total number of response bytes received for this policy."
	::= { vserverScpolicyEntry 22 }

vsvrscpolicyscCurrentSurgeQClients  OBJECT-TYPE
	SYNTAX  Gauge32
	MAX-ACCESS  read-only
	STATUS  current
	DESCRIPTION
		"This counter gives the number of clients that matched the SC policy but are in the surge queue."
	::= { vserverScpolicyEntry 23 }

vsvrscpolicyscCurrentWaitingClients  OBJECT-TYPE
	SYNTAX  Gauge32
	MAX-ACCESS  read-only
	STATUS  current
	DESCRIPTION
		"This counter gives the current number of SC priority clients that are waiting for a server connection for this policy."
	::= { vserverScpolicyEntry 24 }

vsvrscpolicyscTotalServerTransactions  OBJECT-TYPE
	SYNTAX  Counter64
	MAX-ACCESS  read-only
	STATUS  current
	DESCRIPTION
		"This counter gives the number of 200 OK responses received from the server for this policy."
	::= { vserverScpolicyEntry 25 }

vsvrscpolicyscTotalServerTTFBTransactions  OBJECT-TYPE
	SYNTAX  Counter64
	MAX-ACCESS  read-only
	STATUS  current
	DESCRIPTION
		"This counter gives the number of TTFB transcations from the server for this policy."
	::= { vserverScpolicyEntry 26 }

vsvrscpolicyscTotalServerTTLB  OBJECT-TYPE
	SYNTAX  Counter64
	MAX-ACCESS  read-only
	STATUS  current
	DESCRIPTION
		"This counter gives the server TTLB calculated for this policy."
	::= { vserverScpolicyEntry 27 }

vsvrscpolicyscTotalClientTTLB  OBJECT-TYPE
	SYNTAX  Counter64
	MAX-ACCESS  read-only
	STATUS  current
	DESCRIPTION
		"This counter gives the client TTLB calculated for this policy."
	::= { vserverScpolicyEntry 28 }

vsvrscpolicyscTotalServerTTFB  OBJECT-TYPE
	SYNTAX  Counter64
	MAX-ACCESS  read-only
	STATUS  current
	DESCRIPTION
		"This counter gives the server TTFB calculated for this policy."
	::= { vserverScpolicyEntry 29 }

vsvrscpolicyscAverageClientTTLB  OBJECT-TYPE
	SYNTAX  Gauge32
	MAX-ACCESS  read-only
	STATUS  current
	DESCRIPTION
		"This counter gives the average value of the client TTLB for this policy."
	::= { vserverScpolicyEntry 30 }

vsvrscpolicyscAverageServerTTFB  OBJECT-TYPE
	SYNTAX  Gauge32
	MAX-ACCESS  read-only
	STATUS  current
	DESCRIPTION
		"This counter gives the average value of the server TTFB for this policy."
	::= { vserverScpolicyEntry 31 }

vserverAdvanceSslConfigTable  OBJECT-TYPE
	SYNTAX  SEQUENCE OF VserverAdvanceSslConfigEntry
	MAX-ACCESS  not-accessible
	STATUS  current
	DESCRIPTION
		"The vserver advance SSL configuration"
	::= { nsVserverGroup 9 }

vserverAdvanceSslConfigEntry  OBJECT-TYPE
	SYNTAX  VserverAdvanceSslConfigEntry
	MAX-ACCESS  not-accessible
	STATUS  current
	DESCRIPTION
		"..."
	INDEX { vsvrName   }
	::= { vserverAdvanceSslConfigTable 1 }

VserverAdvanceSslConfigEntry ::= SEQUENCE {
	vsvrSslDH  AdminStatus,
	vsvrSslDHCount  Integer32,
	vsvrSslDHFilePath  OCTET STRING,
	vsvrSsleRSA  AdminStatus,
	vsvrSsleRSACount  Integer32,
	vsvrSslv2Protocol  AdminStatus,
	vsvrSslv3Protocol  AdminStatus,
	vsvrSslTLSv1Protocol  AdminStatus,
	vsvrSslRedirectSupport  AdminStatus,
	vsvrSslClearTextPort  Integer32
}

vsvrSslDH  OBJECT-TYPE
	SYNTAX  AdminStatus
	MAX-ACCESS  read-only
	STATUS  current
	DESCRIPTION
		"Whether DH is enabled/disabled."
	::= { vserverAdvanceSslConfigEntry 1 }

vsvrSslDHCount  OBJECT-TYPE
	SYNTAX  Integer32
	MAX-ACCESS  read-only
	STATUS  current
	DESCRIPTION
		"The DH refresh count to re-generate public/private key."
	::= { vserverAdvanceSslConfigEntry 2 }

vsvrSslDHFilePath  OBJECT-TYPE
	SYNTAX  OCTET STRING
	MAX-ACCESS  read-only
	STATUS  current
	DESCRIPTION
		"The DH file path name."
	::= { vserverAdvanceSslConfigEntry 3 }

vsvrSsleRSA  OBJECT-TYPE
	SYNTAX  AdminStatus
	MAX-ACCESS  read-only
	STATUS  current
	DESCRIPTION
		"The ephimeral RSA support for service."
	::= { vserverAdvanceSslConfigEntry 4 }

vsvrSsleRSACount  OBJECT-TYPE
	SYNTAX  Integer32
	MAX-ACCESS  read-only
	STATUS  current
	DESCRIPTION
		"The eRSA refresh count to re-generate RSA temporary key."
	::= { vserverAdvanceSslConfigEntry 5 }

vsvrSslv2Protocol  OBJECT-TYPE
	SYNTAX  AdminStatus
	MAX-ACCESS  read-only
	STATUS  current
	DESCRIPTION
		"The support for SSLv2 protocol for service."
	::= { vserverAdvanceSslConfigEntry 6 }

vsvrSslv3Protocol  OBJECT-TYPE
	SYNTAX  AdminStatus
	MAX-ACCESS  read-only
	STATUS  current
	DESCRIPTION
		"The support for SSLv3 protocol for service."
	::= { vserverAdvanceSslConfigEntry 7 }

vsvrSslTLSv1Protocol  OBJECT-TYPE
	SYNTAX  AdminStatus
	MAX-ACCESS  read-only
	STATUS  current
	DESCRIPTION
		"The support for  TLSv1 protocol for service."
	::= { vserverAdvanceSslConfigEntry 8 }

vsvrSslRedirectSupport  OBJECT-TYPE
	SYNTAX  AdminStatus
	MAX-ACCESS  read-only
	STATUS  current
	DESCRIPTION
		"The support for ssl redirect for service."
	::= { vserverAdvanceSslConfigEntry 9 }

vsvrSslClearTextPort  OBJECT-TYPE
	SYNTAX  Integer32
	MAX-ACCESS  read-only
	STATUS  current
	DESCRIPTION
		"The clear text port on the backend webserver."
	::= { vserverAdvanceSslConfigEntry 10 }

vserverCipherBindingTable  OBJECT-TYPE
	SYNTAX  SEQUENCE OF VserverCipherBindingEntry
	MAX-ACCESS  not-accessible
	STATUS  current
	DESCRIPTION
		"The vserver cipher bindings table"
	::= { nsVserverGroup 10 }

vserverCipherBindingEntry  OBJECT-TYPE
	SYNTAX  VserverCipherBindingEntry
	MAX-ACCESS  not-accessible
	STATUS  current
	DESCRIPTION
		"..."
	INDEX { vsvrName , vsvrSslCipherBindName }
	::= { vserverCipherBindingTable 1 }

VserverCipherBindingEntry ::= SEQUENCE {
	vsvrSslCipherBindName  OCTET STRING,
	vsvrSslCipherBindDesc  OCTET STRING
}

vsvrSslCipherBindName  OBJECT-TYPE
	SYNTAX  OCTET STRING
	MAX-ACCESS  read-only
	STATUS  current
	DESCRIPTION
		"The cipher name bound to this service."
	::= { vserverCipherBindingEntry 1 }

vsvrSslCipherBindDesc  OBJECT-TYPE
	SYNTAX  OCTET STRING
	MAX-ACCESS  read-only
	STATUS  current
	DESCRIPTION
		"The Cipher description."
	::= { vserverCipherBindingEntry 2 }

nsSnmpEventsGroup OBJECT IDENTIFIER
	::= { rs9000 10 }

snmpTrapVarBindOidsGroup OBJECT IDENTIFIER
	::= { nsSnmpEventsGroup 2 }

alarmHighThreshold  OBJECT-TYPE
	SYNTAX  Gauge32
	MAX-ACCESS  accessible-for-notify
	STATUS  current
	DESCRIPTION
		"This is the high threshold value configured for this alarm. When this threshold is crossed an SNMP alarm is generated."
	::= { snmpTrapVarBindOidsGroup 1 }

alarmNormalThreshold  OBJECT-TYPE
	SYNTAX  Gauge32
	MAX-ACCESS  accessible-for-notify
	STATUS  current
	DESCRIPTION
		"This is the normal threshold configured for this alarm which triggers the return-to-normal alarm."
	::= { snmpTrapVarBindOidsGroup 2 }

entityName  OBJECT-TYPE
	SYNTAX  OCTET STRING
	MAX-ACCESS  accessible-for-notify
	STATUS  current
	DESCRIPTION
		"This represents the name of the entity whose state has changed."
	::= { snmpTrapVarBindOidsGroup 3 }

nsUserName  OBJECT-TYPE
	SYNTAX  OCTET STRING
	MAX-ACCESS  accessible-for-notify
	STATUS  current
	DESCRIPTION
		"This represents the name of the system user."
	::= { snmpTrapVarBindOidsGroup 4 }

configurationCmd  OBJECT-TYPE
	SYNTAX  OCTET STRING
	MAX-ACCESS  accessible-for-notify
	STATUS  current
	DESCRIPTION
		"This represents the configuartion command that was issued."
	::= { snmpTrapVarBindOidsGroup 5 }

authorizationStatus  OBJECT-TYPE
	SYNTAX  AuthorizationStatus
	MAX-ACCESS  accessible-for-notify
	STATUS  current
	DESCRIPTION
		"This represents the authorization status for an attempted configuration change."
	::= { snmpTrapVarBindOidsGroup 6 }

commandExecutionStatus  OBJECT-TYPE
	SYNTAX  CommandExecutionStatus
	MAX-ACCESS  accessible-for-notify
	STATUS  current
	DESCRIPTION
		"This represents the command execution status for the attempted configuration change."
	::= { snmpTrapVarBindOidsGroup 7 }

unackSynCount  OBJECT-TYPE
	SYNTAX  OCTET STRING
	MAX-ACCESS  accessible-for-notify
	STATUS  current
	DESCRIPTION
		"The number of un-acknowledged SYNs NetScaler has received in the past synFlood time-interval."
	::= { snmpTrapVarBindOidsGroup 8 }

alarmLowThreshold  OBJECT-TYPE
	SYNTAX  Gauge32
	MAX-ACCESS  accessible-for-notify
	STATUS  current
	DESCRIPTION
		"This is the low threshold value configured for this alarm. When this threshold is crossed an SNMP alarm is generated."
	::= { snmpTrapVarBindOidsGroup 9 }

alarmProbeFailedErrorString  OBJECT-TYPE
	SYNTAX  OCTET STRING
	MAX-ACCESS  accessible-for-notify
	STATUS  current
	DESCRIPTION
		"This string represents the error occured on the last monitor probe failure."
	::= { snmpTrapVarBindOidsGroup 10 }

alarmVipRhiIpAddr  OBJECT-TYPE
	SYNTAX  IpAddress
	MAX-ACCESS  accessible-for-notify
	STATUS  current
	DESCRIPTION
		"This represents the VIP whose RHI state has changed."
	::= { snmpTrapVarBindOidsGroup 11 }

alarmVipRhiState  OBJECT-TYPE
	SYNTAX  EntityState
	MAX-ACCESS  accessible-for-notify
	STATUS  current
	DESCRIPTION
		"This represents the changed RHI state of the VIP."
	::= { snmpTrapVarBindOidsGroup 12 }

alarmRateLmtThresholdExceeded  OBJECT-TYPE
	SYNTAX  OCTET STRING
	MAX-ACCESS  accessible-for-notify
	STATUS  current
	DESCRIPTION
		"This specifies the name of the rate limit identifier that exceeded the threshold."
	::= { snmpTrapVarBindOidsGroup 13 }

ipAddressGathered  OBJECT-TYPE
	SYNTAX  OCTET STRING
	MAX-ACCESS  accessible-for-notify
	STATUS  current
	DESCRIPTION
		"This specifies the list of ip addresses that may have been gathered during the expression evaluation."
	::= { snmpTrapVarBindOidsGroup 14 }

stringComputed  OBJECT-TYPE
	SYNTAX  OCTET STRING
	MAX-ACCESS  accessible-for-notify
	STATUS  current
	DESCRIPTION
		"This contains the string computed during the expression evaluation."
	::= { snmpTrapVarBindOidsGroup 15 }

alarmEntityCurState  OBJECT-TYPE
	SYNTAX  EntityState
	MAX-ACCESS  accessible-for-notify
	STATUS  current
	DESCRIPTION
		"This represents the state of vserver, physicalservice or servicegroup."
	::= { snmpTrapVarBindOidsGroup 16 }

sysHealthPowerSupplyStatus  OBJECT-TYPE
	SYNTAX  OCTET STRING
	MAX-ACCESS  accessible-for-notify
	STATUS  current
	DESCRIPTION
		"This text represents the status of power supply unit"
	::= { snmpTrapVarBindOidsGroup 17 }

alarmCurrentValue  OBJECT-TYPE
	SYNTAX  Gauge32
	MAX-ACCESS  accessible-for-notify
	STATUS  current
	DESCRIPTION
		"This is the current value of the entity when high or normal threshold trap is sent."
	::= { snmpTrapVarBindOidsGroup 18 }

alarmVipRhiInetAddressType  OBJECT-TYPE
	SYNTAX  InetAddressType
	MAX-ACCESS  accessible-for-notify
	STATUS  current
	DESCRIPTION
		"The address type of alarmVipRhiInetAddress"
	::= { snmpTrapVarBindOidsGroup 19 }

alarmVipRhiInetAddress  OBJECT-TYPE
	SYNTAX  InetAddress
	MAX-ACCESS  accessible-for-notify
	STATUS  current
	DESCRIPTION
		"This represents the VIP whose RHI state has changed."
	::= { snmpTrapVarBindOidsGroup 20 }

netScalerEventsV2 OBJECT-IDENTITY
	STATUS  current
	DESCRIPTION
		"The events for NetScaler"
	::= { netScalerEvents 0 }

changeToPrimary  NOTIFICATION-TYPE
	OBJECTS  { sysIpAddress }
	STATUS  current
	DESCRIPTION
		"This trap indicates that the netscaler is now operating in the primary mode."
	::= { netScalerEventsV2 1 }

changeToSecondary  NOTIFICATION-TYPE
	OBJECTS  { sysIpAddress }
	STATUS  current
	DESCRIPTION
		"This trap indicates that the netscaler is now operating in the Secondary mode."
	::= { netScalerEventsV2 2 }

cpuUtilization  NOTIFICATION-TYPE
	OBJECTS  { nsCPUusage , alarmHighThreshold , sysIpAddress }
	STATUS  current
	DESCRIPTION
		"This trap indicates that the CPU utilization has exceeded the high threshold"
	::= { netScalerEventsV2 3 }

linkUp  NOTIFICATION-TYPE
	STATUS  obsolete
	DESCRIPTION
		"0"
	::= { netScalerEventsV2 4 }

linkDown  NOTIFICATION-TYPE
	STATUS  obsolete
	DESCRIPTION
		"0"
	::= { netScalerEventsV2 5 }

discoverFailure  NOTIFICATION-TYPE
	STATUS  obsolete
	DESCRIPTION
		"0"
	::= { netScalerEventsV2 6 }

memUtilization  NOTIFICATION-TYPE
	STATUS  obsolete
	DESCRIPTION
		"0"
	::= { netScalerEventsV2 7 }

entitydown  NOTIFICATION-TYPE
	OBJECTS  { entityName , sysIpAddress }
	STATUS  current
	DESCRIPTION
		"This trap is sent when the state of entities such as an interface, vserver, physicalservice or servicegroup changes to DOWN"
	::= { netScalerEventsV2 8 }

entityup  NOTIFICATION-TYPE
	OBJECTS  { entityName , sysIpAddress }
	STATUS  current
	DESCRIPTION
		"This trap is sent when the state of entities such as an interface, vserver, physicalservice or servicegroup changes to UP"
	::= { netScalerEventsV2 9 }

synflood  NOTIFICATION-TYPE
	OBJECTS  { unackSynCount , alarmHighThreshold , sysIpAddress }
	STATUS  current
	DESCRIPTION
		"This trap is sent when the rate at which unacknowledged SYNs are received cross a threshold value"
	::= { netScalerEventsV2 10 }

cpuUtilizationNormal  NOTIFICATION-TYPE
	OBJECTS  { nsCPUusage , alarmNormalThreshold , sysIpAddress }
	STATUS  current
	DESCRIPTION
		"This trap indicates that the CPU utilization has come back to normal"
	::= { netScalerEventsV2 11 }

synfloodNormal  NOTIFICATION-TYPE
	OBJECTS  { unackSynCount , alarmNormalThreshold , sysIpAddress }
	STATUS  current
	DESCRIPTION
		"This trap is sent when the rate at which unacknowledged SYNs are received returns to normal"
	::= { netScalerEventsV2 12 }

memoryUtilization  NOTIFICATION-TYPE
	OBJECTS  { resMemUsage , alarmHighThreshold , sysIpAddress }
	STATUS  current
	DESCRIPTION
		"This trap is sent when the memory utilization of the system exceeds the threshold value"
	::= { netScalerEventsV2 13 }

memoryUtilizationNormal  NOTIFICATION-TYPE
	OBJECTS  { resMemUsage , alarmNormalThreshold , sysIpAddress }
	STATUS  current
	DESCRIPTION
		"This trap is sent when the memory utilization of the system returns to normal"
	::= { netScalerEventsV2 14 }

vServerRequestRate  NOTIFICATION-TYPE
	OBJECTS  { vsvrName , vsvrRequestRate , alarmHighThreshold , vsvrFullName , sysIpAddress }
	STATUS  current
	DESCRIPTION
		"This trap is sent when the request rate on a vServer exceeds a threshold value"
	::= { netScalerEventsV2 15 }

vServerRequestRateNormal  NOTIFICATION-TYPE
	OBJECTS  { vsvrName , vsvrRequestRate , alarmNormalThreshold , vsvrFullName , sysIpAddress }
	STATUS  current
	DESCRIPTION
		"This trap is sent when the request rate on a vServer returns to normal"
	::= { netScalerEventsV2 16 }

serviceRequestRate  NOTIFICATION-TYPE
	OBJECTS  { svcServiceName , svcRequestRate , alarmHighThreshold , svcServiceFullName , sysIpAddress }
	STATUS  current
	DESCRIPTION
		"This trap is sent when the request rate on a service exceeds a threshold value"
	::= { netScalerEventsV2 17 }

serviceRequestRateNormal  NOTIFICATION-TYPE
	OBJECTS  { svcServiceName , svcRequestRate , alarmNormalThreshold , svcServiceFullName , sysIpAddress }
	STATUS  current
	DESCRIPTION
		"This trap is sent when the request rate on a service returns to normal"
	::= { netScalerEventsV2 18 }

entityRxRate  NOTIFICATION-TYPE
	STATUS  obsolete
	DESCRIPTION
		"0"
	::= { netScalerEventsV2 19 }

entityRxRateNormal  NOTIFICATION-TYPE
	STATUS  obsolete
	DESCRIPTION
		"0"
	::= { netScalerEventsV2 20 }

entityTxRate  NOTIFICATION-TYPE
	STATUS  obsolete
	DESCRIPTION
		"0"
	::= { netScalerEventsV2 21 }

entityTxRateNormal  NOTIFICATION-TYPE
	STATUS  obsolete
	DESCRIPTION
		"0"
	::= { netScalerEventsV2 22 }

entitySynflood  NOTIFICATION-TYPE
	STATUS  obsolete
	DESCRIPTION
		"0"
	::= { netScalerEventsV2 23 }

entitySynfloodNormal  NOTIFICATION-TYPE
	STATUS  obsolete
	DESCRIPTION
		"0"
	::= { netScalerEventsV2 24 }

netScalerConfigChange  NOTIFICATION-TYPE
	OBJECTS  { nsUserName , configurationCmd , authorizationStatus , commandExecutionStatus , sysIpAddress }
	STATUS  current
	DESCRIPTION
		"This trap is sent when the configuration on the NetScaler is changed."
	::= { netScalerEventsV2 25 }

maxClients  NOTIFICATION-TYPE
	OBJECTS  { svcServiceName , svcEstablishedConn , alarmHighThreshold , svcServiceFullName , sysIpAddress }
	STATUS  current
	DESCRIPTION
		"This trap is sent when the number of clients hits the maxClients value for a service"
	::= { netScalerEventsV2 26 }

maxClientsNormal  NOTIFICATION-TYPE
	OBJECTS  { svcServiceName , svcEstablishedConn , alarmNormalThreshold , svcServiceFullName , sysIpAddress }
	STATUS  current
	DESCRIPTION
		"This trap is sent when the number of clients falls below 70% of maxClients value for a service."
	::= { netScalerEventsV2 27 }

netScalerConfigSave  NOTIFICATION-TYPE
	OBJECTS  { nsUserName , sysIpAddress }
	STATUS  current
	DESCRIPTION
		"This trap is sent when the configuration on the NetScaler is saved."
	::= { netScalerEventsV2 28 }

serviceRxBytesRate  NOTIFICATION-TYPE
	OBJECTS  { svcServiceName , svcRxBytesRate , alarmHighThreshold , svcServiceFullName , sysIpAddress }
	STATUS  current
	DESCRIPTION
		"This trap is sent when the request bytes/s of a service exceeds a threshold value."
	::= { netScalerEventsV2 29 }

serviceRxBytesRateNormal  NOTIFICATION-TYPE
	OBJECTS  { svcServiceName , svcRxBytesRate , alarmNormalThreshold , svcServiceFullName , sysIpAddress }
	STATUS  current
	DESCRIPTION
		"This trap is sent when the request bytes/s of a service returns to normal."
	::= { netScalerEventsV2 30 }

vserverRxBytesRate  NOTIFICATION-TYPE
	OBJECTS  { vsvrName , vsvrRxBytesRate , alarmHighThreshold , vsvrFullName , sysIpAddress }
	STATUS  current
	DESCRIPTION
		"This trap is sent when the request bytes/s of a vserver exceeds a threshold value."
	::= { netScalerEventsV2 31 }

vserverRxBytesRateNormal  NOTIFICATION-TYPE
	OBJECTS  { vsvrName , vsvrRxBytesRate , alarmNormalThreshold , vsvrFullName , sysIpAddress }
	STATUS  current
	DESCRIPTION
		"This trap is sent when the request bytes/s of a vServer returns to normal."
	::= { netScalerEventsV2 32 }

serviceTxBytesRate  NOTIFICATION-TYPE
	OBJECTS  { svcServiceName , svcTxBytesRate , alarmHighThreshold , svcServiceFullName , sysIpAddress }
	STATUS  current
	DESCRIPTION
		"This trap is sent when the response bytes/s of a service exceeds a threshold value."
	::= { netScalerEventsV2 33 }

serviceTxBytesRateNormal  NOTIFICATION-TYPE
	OBJECTS  { svcServiceName , svcTxBytesRate , alarmNormalThreshold , svcServiceFullName , sysIpAddress }
	STATUS  current
	DESCRIPTION
		"This trap is sent when the response bytes/s of a service returns to normal."
	::= { netScalerEventsV2 34 }

vserverTxBytesRate  NOTIFICATION-TYPE
	OBJECTS  { vsvrName , vsvrTxBytesRate , alarmHighThreshold , vsvrFullName , sysIpAddress }
	STATUS  current
	DESCRIPTION
		"This trap is sent when the response bytes/s of a vserver exceeds a threshold value."
	::= { netScalerEventsV2 35 }

vserverTxBytesRateNormal  NOTIFICATION-TYPE
	OBJECTS  { vsvrName , vsvrTxBytesRate , alarmNormalThreshold , vsvrFullName , sysIpAddress }
	STATUS  current
	DESCRIPTION
		"This trap is sent when the response bytes/s of a vServer returns to normal."
	::= { netScalerEventsV2 36 }

serviceSynfloodRate  NOTIFICATION-TYPE
	OBJECTS  { svcServiceName , svcSynfloodRate , alarmHighThreshold , svcServiceFullName , sysIpAddress }
	STATUS  current
	DESCRIPTION
		"This trap is sent when the number of unacknowledged syns for a service exceeds a threshold value."
	::= { netScalerEventsV2 37 }

serviceSynfloodNormal  NOTIFICATION-TYPE
	OBJECTS  { svcServiceName , svcSynfloodRate , alarmNormalThreshold , svcServiceFullName , sysIpAddress }
	STATUS  current
	DESCRIPTION
		"This trap is sent when the number of unacknowledged syns for a service returns to normal."
	::= { netScalerEventsV2 38 }

vserverSynfloodRate  NOTIFICATION-TYPE
	OBJECTS  { vsvrName , vsvrSynfloodRate , alarmHighThreshold , vsvrFullName , sysIpAddress }
	STATUS  current
	DESCRIPTION
		"This trap is sent when the number of unacknowledged syns for a vserver exceeds a threshold value."
	::= { netScalerEventsV2 39 }

vserverSynfloodNormal  NOTIFICATION-TYPE
	OBJECTS  { vsvrName , vsvrSynfloodRate , alarmNormalThreshold , vsvrFullName , sysIpAddress }
	STATUS  current
	DESCRIPTION
		"This trap is sent when the number of unacknowledged syns for a vserver returns to normal."
	::= { netScalerEventsV2 40 }

svcGroupMemberRequestRate  NOTIFICATION-TYPE
	OBJECTS  { svcGrpMemberName , svcGrpMemberRequestRate , alarmHighThreshold , svcGrpMemberFullName , sysIpAddress }
	STATUS  current
	DESCRIPTION
		"This trap is sent when the request rate on a service group member exceeds a threshold value"
	::= { netScalerEventsV2 41 }

svcGroupMemberRequestRateNormal  NOTIFICATION-TYPE
	OBJECTS  { svcGrpMemberName , svcGrpMemberRequestRate , alarmNormalThreshold , svcGrpMemberFullName , sysIpAddress }
	STATUS  current
	DESCRIPTION
		"This trap is sent when the request rate on a service group member returns to normal"
	::= { netScalerEventsV2 42 }

svcGroupMemberRxBytesRate  NOTIFICATION-TYPE
	OBJECTS  { svcGrpMemberName , svcGrpMemberRxBytesRate , alarmHighThreshold , svcGrpMemberFullName , sysIpAddress }
	STATUS  current
	DESCRIPTION
		"This trap is sent when the request bytes/s of a service group exceeds a threshold value."
	::= { netScalerEventsV2 43 }

svcGroupMemberRxBytesRateNormal  NOTIFICATION-TYPE
	OBJECTS  { svcGrpMemberName , svcGrpMemberRxBytesRate , alarmNormalThreshold , svcGrpMemberFullName , sysIpAddress }
	STATUS  current
	DESCRIPTION
		"This trap is sent when the request bytes/s of a service group returns to normal."
	::= { netScalerEventsV2 44 }

svcGroupMemberTxBytesRate  NOTIFICATION-TYPE
	OBJECTS  { svcGrpMemberName , svcGrpMemberTxBytesRate , alarmHighThreshold , svcGrpMemberFullName , sysIpAddress }
	STATUS  current
	DESCRIPTION
		"This trap is sent when the response bytes/s of a service group exceeds a threshold value."
	::= { netScalerEventsV2 45 }

svcGroupMemberTxBytesRateNormal  NOTIFICATION-TYPE
	OBJECTS  { svcGrpMemberName , svcGrpMemberTxBytesRate , alarmNormalThreshold , svcGrpMemberFullName , sysIpAddress }
	STATUS  current
	DESCRIPTION
		"This trap is sent when the response bytes/s of a service group returns to normal."
	::= { netScalerEventsV2 46 }

svcGroupMemberSynfloodRate  NOTIFICATION-TYPE
	OBJECTS  { svcGrpMemberName , svcGrpMemberSynfloodRate , alarmHighThreshold , svcGrpMemberFullName , sysIpAddress }
	STATUS  current
	DESCRIPTION
		"This trap is sent when the number of unacknowledged syns for a service group exceeds a threshold value."
	::= { netScalerEventsV2 47 }

svcGroupMemberSynfloodNormal  NOTIFICATION-TYPE
	OBJECTS  { svcGrpMemberName , svcGrpMemberSynfloodRate , alarmNormalThreshold , svcGrpMemberFullName , sysIpAddress }
	STATUS  current
	DESCRIPTION
		"This trap is sent when the number of unacknowledged syns for a service group returns to normal."
	::= { netScalerEventsV2 48 }

svcGroupMemberMaxClients  NOTIFICATION-TYPE
	OBJECTS  { svcGrpMemberName , svcGrpMemberEstablishedConn , alarmHighThreshold , svcGrpMemberFullName , sysIpAddress }
	STATUS  current
	DESCRIPTION
		"This trap is sent when the number of clients hits the maxClients value for a service group member"
	::= { netScalerEventsV2 49 }

svcGroupMemberMaxClientsNormal  NOTIFICATION-TYPE
	OBJECTS  { svcGrpMemberName , svcGrpMemberEstablishedConn , alarmNormalThreshold , svcGrpMemberFullName , sysIpAddress }
	STATUS  current
	DESCRIPTION
		"This trap is sent when the number of clients falls below 70% of maxClients value for a service group member."
	::= { netScalerEventsV2 50 }

averageCpuUtilization  NOTIFICATION-TYPE
	OBJECTS  { resCpuUsage , alarmHighThreshold , sysIpAddress }
	STATUS  current
	DESCRIPTION
		"This trap indicates that the average CPU usage in the multi-processor NetScaler system has exceeded the high threshold."
	::= { netScalerEventsV2 51 }

averageCpuUtilizationNormal  NOTIFICATION-TYPE
	OBJECTS  { resCpuUsage , alarmNormalThreshold , sysIpAddress }
	STATUS  current
	DESCRIPTION
		"This trap indicates that the average CPU usage in the multi-processor NetScaler system has come back to normal."
	::= { netScalerEventsV2 52 }

monRespTimeoutAboveThresh  NOTIFICATION-TYPE
	OBJECTS  { monServiceName , monitorName , responseTimeoutThreshold , alarmMonrespto , sysIpAddress }
	STATUS  current
	DESCRIPTION
		"This trap is sent when the response timeout for a monitor probe exceeds the configured threshold."
	::= { netScalerEventsV2 53 }

monRespTimeoutBelowThresh  NOTIFICATION-TYPE
	OBJECTS  { monServiceName , monitorName , responseTimeoutThreshold , alarmMonrespto , sysIpAddress }
	STATUS  current
	DESCRIPTION
		"This trap is sent when the response timeout for a monitor probe comes back to normal, less than the threshold set."
	::= { netScalerEventsV2 54 }

netScalerLoginFailure  NOTIFICATION-TYPE
	OBJECTS  { nsUserName , sysIpAddress }
	STATUS  current
	DESCRIPTION
		"This trap is sent when a login attempt to the NetScaler fails."
	::= { netScalerEventsV2 55 }

sslCertificateExpiry  NOTIFICATION-TYPE
	OBJECTS  { sslCertKeyName , sslDaysToExpire , sysIpAddress }
	STATUS  current
	DESCRIPTION
		"This trap is sent as an advance notification when an SSL certificate is due to expire."
	::= { netScalerEventsV2 56 }

fanSpeedLow  NOTIFICATION-TYPE
	OBJECTS  { sysHealthCounterName , sysHealthCounterValue , alarmLowThreshold , sysIpAddress }
	STATUS  current
	DESCRIPTION
		"This trap indicates that a fan speed has gone below an alarm threshold."
	::= { netScalerEventsV2 57 }

fanSpeedNormal  NOTIFICATION-TYPE
	OBJECTS  { sysHealthCounterName , sysHealthCounterValue , alarmNormalThreshold , sysIpAddress }
	STATUS  current
	DESCRIPTION
		"This trap indicates that a fan speed has returned to normal."
	::= { netScalerEventsV2 58 }

voltageLow  NOTIFICATION-TYPE
	OBJECTS  { sysHealthCounterName , sysHealthCounterValue , alarmLowThreshold , sysIpAddress }
	STATUS  current
	DESCRIPTION
		"This trap indicates that a voltage has gone low."
	::= { netScalerEventsV2 59 }

voltageNormal  NOTIFICATION-TYPE
	OBJECTS  { sysHealthCounterName , sysHealthCounterValue , alarmNormalThreshold , sysIpAddress }
	STATUS  current
	DESCRIPTION
		"This trap indicates that a voltage has returned to normal."
	::= { netScalerEventsV2 60 }

voltageHigh  NOTIFICATION-TYPE
	OBJECTS  { sysHealthCounterName , sysHealthCounterValue , alarmHighThreshold , sysIpAddress }
	STATUS  current
	DESCRIPTION
		"This trap indicates that a voltage has gone high."
	::= { netScalerEventsV2 61 }

temperatureHigh  NOTIFICATION-TYPE
	OBJECTS  { sysHealthCounterName , sysHealthCounterValue , alarmHighThreshold , sysIpAddress }
	STATUS  current
	DESCRIPTION
		"This trap indicates that a temperature has gone high."
	::= { netScalerEventsV2 62 }

temperatureNormal  NOTIFICATION-TYPE
	OBJECTS  { sysHealthCounterName , sysHealthCounterValue , alarmNormalThreshold , sysIpAddress }
	STATUS  current
	DESCRIPTION
		"This trap indicates that a temperature has returned to normal."
	::= { netScalerEventsV2 63 }

diskUsageHigh  NOTIFICATION-TYPE
	OBJECTS  { sysHealthDiskName , sysHealthDiskPerusage , alarmHighThreshold , sysIpAddress }
	STATUS  current
	DESCRIPTION
		"This trap indicates that disk usage has gone high."
	::= { netScalerEventsV2 64 }

diskUsageNormal  NOTIFICATION-TYPE
	OBJECTS  { sysHealthDiskName , sysHealthDiskPerusage , alarmNormalThreshold , sysIpAddress }
	STATUS  current
	DESCRIPTION
		"This trap indicates that disk usage has returned to normal."
	::= { netScalerEventsV2 65 }

interfaceThroughputLow  NOTIFICATION-TYPE
	OBJECTS  { ifName , ifThroughput , ifMinThroughput , sysIpAddress }
	STATUS  current
	DESCRIPTION
		"This trap indicates that interface throughput is low."
	::= { netScalerEventsV2 66 }

interfaceThroughputNormal  NOTIFICATION-TYPE
	OBJECTS  { ifName , ifThroughput , ifMinThroughput , sysIpAddress }
	STATUS  current
	DESCRIPTION
		"This trap indicates that interface throughput has returned to normal."
	::= { netScalerEventsV2 67 }

haVersionMismatch  NOTIFICATION-TYPE
	OBJECTS  { sysIpAddress }
	STATUS  current
	DESCRIPTION
		"This trap indicates that there is a mismatch in the OS version of the netscalers participating in HA. "
	::= { netScalerEventsV2 68 }

haSyncFailure  NOTIFICATION-TYPE
	OBJECTS  { sysIpAddress }
	STATUS  current
	DESCRIPTION
		"This trap indicates that config synchronization has failed on secondary. "
	::= { netScalerEventsV2 69 }

haNoHeartbeats  NOTIFICATION-TYPE
	OBJECTS  { haNicsMonitorFailed , sysIpAddress }
	STATUS  current
	DESCRIPTION
		"This trap indicates that HA heartbeats are not received from the secondary. "
	::= { netScalerEventsV2 70 }

haBadSecState  NOTIFICATION-TYPE
	OBJECTS  { haPeerSystemState , sysIpAddress }
	STATUS  current
	DESCRIPTION
		"This trap indicates that the secondary is in DOWN/UNKNOWN/STAY SECONDARY state. "
	::= { netScalerEventsV2 71 }

interfaceBWUseHigh  NOTIFICATION-TYPE
	OBJECTS  { ifName , alarmHighThreshold , alarmCurrentValue , sysIpAddress }
	STATUS  current
	DESCRIPTION
		"This trap is sent when the bandwidth usage of any of the interfaces of the system exceeds the threshold value (configured in Mbits/second)"
	::= { netScalerEventsV2 72 }

interfaceBWUseNormal  NOTIFICATION-TYPE
	OBJECTS  { ifName , alarmNormalThreshold , alarmCurrentValue , sysIpAddress }
	STATUS  current
	DESCRIPTION
		"This trap is sent when the bandwidth usage of any of the interfaces of the system returns to normal"
	::= { netScalerEventsV2 73 }

aggregateBWUseHigh  NOTIFICATION-TYPE
	OBJECTS  { alarmHighThreshold , alarmCurrentValue , sysIpAddress }
	STATUS  current
	DESCRIPTION
		"This trap is sent when the aggregate bandwidth usage of the system exceeds the threshold value (configured in Mbits/second) "
	::= { netScalerEventsV2 74 }

aggregateBWUseNormal  NOTIFICATION-TYPE
	OBJECTS  { alarmNormalThreshold , alarmCurrentValue , sysIpAddress }
	STATUS  current
	DESCRIPTION
		"This trap is sent when the aggregate bandwidth usage of the system returns to normal."
	::= { netScalerEventsV2 75 }

vserverRhiStateChange  NOTIFICATION-TYPE
	OBJECTS  { alarmVipRhiState , alarmVipRhiInetAddressType , alarmVipRhiInetAddress , sysIpAddress }
	STATUS  current
	DESCRIPTION
		"This trap is sent when the vserver RHI state changes."
	::= { netScalerEventsV2 76 }

rateLmtThresholdExceed  NOTIFICATION-TYPE
	OBJECTS  { alarmRateLmtThresholdExceeded , ipAddressGathered , stringComputed , sysIpAddress }
	STATUS  current
	DESCRIPTION
		"This trap is sent when the client exceeds the ratelimit threshold. "
	::= { netScalerEventsV2 77 }

monProbeFailed  NOTIFICATION-TYPE
	OBJECTS  { monServiceName , monitorName , alarmProbeFailedRetries , monitorRetrys , alarmProbeFailedErrorString , sysIpAddress }
	STATUS  current
	DESCRIPTION
		"This trap is sent when the monitor probe fails for configured number of retries in given max retries attempts."
	::= { netScalerEventsV2 78 }

temperatureCpuHigh  NOTIFICATION-TYPE
	OBJECTS  { sysHealthCounterName , sysHealthCounterValue , alarmHighThreshold , sysIpAddress }
	STATUS  current
	DESCRIPTION
		"This trap indicates that a CPU temperature has gone high."
	::= { netScalerEventsV2 79 }

temperatureCpuNormal  NOTIFICATION-TYPE
	OBJECTS  { sysHealthCounterName , sysHealthCounterValue , alarmNormalThreshold , sysIpAddress }
	STATUS  current
	DESCRIPTION
		"This trap indicates that a CPU temperature has returned to normal."
	::= { netScalerEventsV2 80 }

entityofs  NOTIFICATION-TYPE
	OBJECTS  { entityName , alarmEntityCurState , sysIpAddress }
	STATUS  current
	DESCRIPTION
		"This trap is sent when the state of entities such as vserver, physicalservice or servicegroup changes to OUT OF SERVICE"
	::= { netScalerEventsV2 81 }

powerSupplyFailed  NOTIFICATION-TYPE
	OBJECTS  { sysHealthCounterName , sysHealthCounterValue , sysHealthPowerSupplyStatus , sysIpAddress }
	STATUS  current
	DESCRIPTION
		"This trap is sent when power supply has failed or disconnected from the system"
	::= { netScalerEventsV2 82 }

powerSupplyNormal  NOTIFICATION-TYPE
	OBJECTS  { sysHealthCounterName , sysHealthCounterValue , sysHealthPowerSupplyStatus , sysIpAddress }
	STATUS  current
	DESCRIPTION
		"This trap is sent when power supply status returned back to normal"
	::= { netScalerEventsV2 83 }

END -- end of module NS-ROOT-MIB.
