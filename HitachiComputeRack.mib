-- 00-00
--------------------------------------------------------------------------------
HitachiComputeRackEx-MIB DEFINITIONS ::= BEGIN

IMPORTS
	OBJECT-TYPE, MODULE-IDENTITY, NOTIFICATION-TYPE, enterprises,
	Integer32
		FROM SNMPv2-SMI
	TEXTUAL-CONVENTION, DisplayString
		FROM SNMPv2-TC;

computeRack  MODULE-IDENTITY
	LAST-UPDATED "201204051253Z"
	ORGANIZATION "Hitachi, Ltd."
	CONTACT-INFO ""
	DESCRIPTION
		"This shows the information of hitachi Compute Rack."
::= { compute 2 }

hitachi                                  OBJECT IDENTIFIER ::= { enterprises 116 }

systemExMib                              OBJECT IDENTIFIER ::= { hitachi 5 }

compute                                  OBJECT IDENTIFIER ::= { systemExMib 52 }

chassis                                  OBJECT IDENTIFIER ::= { computeRack 1 }

chassisBasicInfo                         OBJECT IDENTIFIER ::= { chassis 1 }

chassisInfoType                          OBJECT-TYPE
	SYNTAX     INTEGER {
		Rackmount(1), Blade(2), Tower(3), unknown(4)
	}
	MAX-ACCESS read-only
	STATUS     current
	DESCRIPTION
		"This shows the chassis type of server chassis."
	::= { chassisBasicInfo 1 }

chassisInfoProductName                   OBJECT-TYPE
	SYNTAX     DisplayString
	MAX-ACCESS read-only
	STATUS     current
	DESCRIPTION
		"This shows the product name of server chassis."
	::= { chassisBasicInfo 2 }

chassisInfoModel                         OBJECT-TYPE
	SYNTAX     DisplayString
	MAX-ACCESS read-only
	STATUS     current
	DESCRIPTION
		"This shows the model of server chassis."
	::= { chassisBasicInfo 3 }

chassisInfoSerialNum                     OBJECT-TYPE
	SYNTAX     DisplayString
	MAX-ACCESS read-only
	STATUS     current
	DESCRIPTION
		"This shows the serial number of server chassis."
	::= { chassisBasicInfo 4 }

chassisInfoProductVersion                OBJECT-TYPE
	SYNTAX     DisplayString
	MAX-ACCESS read-only
	STATUS     current
	DESCRIPTION
		"This shows the model version of server chassis."
	::= { chassisBasicInfo 5 }

chassisInfoProductManufacturer           OBJECT-TYPE
	SYNTAX     DisplayString
	MAX-ACCESS read-only
	STATUS     current
	DESCRIPTION
		"This shows the product manufacturer of chassis."
	::= { chassisBasicInfo 6 }

chassisInfoChassisID                     OBJECT-TYPE
	SYNTAX     DisplayString
	MAX-ACCESS read-only
	STATUS     current
	DESCRIPTION
		"This shows the chassis ID of server chassis."
	::= { chassisBasicInfo 7 }

chassisInfoBoardProductName              OBJECT-TYPE
	SYNTAX     DisplayString
	MAX-ACCESS read-only
	STATUS     current
	DESCRIPTION
		"This shows the product name of board."
	::= { chassisBasicInfo 8 }

chassisInfoBoardSerialNum                OBJECT-TYPE
	SYNTAX     DisplayString
	MAX-ACCESS read-only
	STATUS     current
	DESCRIPTION
		"This shows the serial number of board."
	::= { chassisBasicInfo 9 }

chassisInfoBoardManufacturer             OBJECT-TYPE
	SYNTAX     DisplayString
	MAX-ACCESS read-only
	STATUS     current
	DESCRIPTION
		"This shows the product manufacturer of board."
	::= { chassisBasicInfo 10 }

chassisInfoUUID                          OBJECT-TYPE
	SYNTAX     DisplayString
	MAX-ACCESS read-only
	STATUS     current
	DESCRIPTION
		"This shows UUID(universal Unique ID) of server chassis."
	::= { chassisBasicInfo 11 }

chassisInfoLogicalPartitionSupport       OBJECT-TYPE
	SYNTAX     INTEGER {
		not-support(1), support(2), unknown(3)
	}
	MAX-ACCESS read-only
	STATUS     current
	DESCRIPTION
		"This shows whether the chassis supports HVM or not."
	::= { chassisBasicInfo 12 }

chassisInfoRemoteKVMSupport              OBJECT-TYPE
	SYNTAX     INTEGER {
		not-support(1), support(2), unknown(3)
	}
	MAX-ACCESS read-only
	STATUS     current
	DESCRIPTION
		"This shows whether the server chassis supports remote KVM or not of server chassis."
	::= { chassisBasicInfo 13 }

chassisInfoSpec                          OBJECT IDENTIFIER ::= { chassisBasicInfo 20 }

chassisSpecInputCurrentType              OBJECT-TYPE
	SYNTAX     INTEGER {
		ac(1), dc(2), unknown(3)
	}
	MAX-ACCESS read-only
	STATUS     current
	DESCRIPTION
		"This shows the currency type of server chassis."
	::= { chassisInfoSpec 1 }

chassisSpecRateVoltage                   OBJECT-TYPE
	SYNTAX     Integer32
	UNITS      "0.1 V"
	MAX-ACCESS read-only
	STATUS     current
	DESCRIPTION
		"This shows the voltage of server chassis."
	::= { chassisInfoSpec 2 }

chassisSpecTempUpperLimit                OBJECT-TYPE
	SYNTAX     Integer32
	UNITS      "0.1 degrees C"
	MAX-ACCESS read-only
	STATUS     current
	DESCRIPTION
		"This shows the upper temperature of sensor in server chassis."
	::= { chassisInfoSpec 3 }

chassisSpecTempLowerLimit                OBJECT-TYPE
	SYNTAX     Integer32
	UNITS      "0.1 degrees C"
	MAX-ACCESS read-only
	STATUS     current
	DESCRIPTION
		"This shows the lower temperature of sensor in server chassis."
	::= { chassisInfoSpec 4 }

chassisSpecConsumptionCurrent            OBJECT-TYPE
	SYNTAX     Integer32
	UNITS      "0.1 A"
	MAX-ACCESS read-only
	STATUS     current
	DESCRIPTION
		"This shows the maximum currency of server chassis in current configuration"
	::= { chassisInfoSpec 5 }

chassisSpecPowerConsumption              OBJECT-TYPE
	SYNTAX     Integer32
	UNITS      "0.1 kW"
	MAX-ACCESS read-only
	STATUS     current
	DESCRIPTION
		"This shows the maximum power consumption of server chassis in current configuration."
	::= { chassisInfoSpec 6 }

chassisSpecConsumptionCurrentMaxConfig   OBJECT-TYPE
	SYNTAX     Integer32
	UNITS      "0.1 A"
	MAX-ACCESS read-only
	STATUS     current
	DESCRIPTION
		"This shows the maximum currency of server chassis in largest configuration."
	::= { chassisInfoSpec 7 }

chassisSpecPowerConsumptionMaxConfig     OBJECT-TYPE
	SYNTAX     Integer32
	UNITS      "0.1 kW"
	MAX-ACCESS read-only
	STATUS     current
	DESCRIPTION
		"This shows the maximum power consumption of server chassis in largest configuration."
	::= { chassisInfoSpec 8 }

chassisSpecMaxAirVolume                  OBJECT-TYPE
	SYNTAX     Integer32
	UNITS      "0.1 m^3/min"
	MAX-ACCESS read-only
	STATUS     current
	DESCRIPTION
		"This shows the current air volume of server chassis."
	::= { chassisInfoSpec 9 }

chassisSpecHeight                        OBJECT-TYPE
	SYNTAX     Integer32
	UNITS      "U"
	MAX-ACCESS read-only
	STATUS     current
	DESCRIPTION
		"This shows the height of server chassis."
	::= { chassisInfoSpec 10 }

chassisSpecTotalMass                     OBJECT-TYPE
	SYNTAX     Integer32
	UNITS      "0.1 kg"
	MAX-ACCESS read-only
	STATUS     current
	DESCRIPTION
		"This shows the total mass of server chassis."
	::= { chassisInfoSpec 11 }

chassisSpecSize                          OBJECT-TYPE
	SYNTAX     DisplayString
	MAX-ACCESS read-only
	STATUS     current
	DESCRIPTION
		"This shows the size of server chassis."
	::= { chassisInfoSpec 12 }

chassisCapacity                          OBJECT IDENTIFIER ::= { chassis 2 }

chassisCapacityCPUSocket                 OBJECT-TYPE
	SYNTAX     Integer32
	MAX-ACCESS read-only
	STATUS     current
	DESCRIPTION
		"This shows the capacity of CPU sockets of server chassis."
	::= { chassisCapacity 1 }

chassisCapacityDIMMSlot                  OBJECT-TYPE
	SYNTAX     Integer32
	MAX-ACCESS read-only
	STATUS     current
	DESCRIPTION
		"This shows the capacity of DIMM slots of server chassis."
	::= { chassisCapacity 2 }

chassisCapacityPCISlot                   OBJECT-TYPE
	SYNTAX     Integer32
	MAX-ACCESS read-only
	STATUS     current
	DESCRIPTION
		"This shows the capacity of PCI slots of server chassis."
	::= { chassisCapacity 3 }

chassisCapacityLOM                       OBJECT-TYPE
	SYNTAX     Integer32
	MAX-ACCESS read-only
	STATUS     current
	DESCRIPTION
		"This shows the capacity of onboard LAN ports of server chassis."
	::= { chassisCapacity 4 }

chassisCapacityFan                       OBJECT-TYPE
	SYNTAX     Integer32
	MAX-ACCESS read-only
	STATUS     current
	DESCRIPTION
		"This shows the capacity of onboard fans of server chassis."
	::= { chassisCapacity 5 }

chassisCapacityHDDSlot                   OBJECT-TYPE
	SYNTAX     Integer32
	MAX-ACCESS read-only
	STATUS     current
	DESCRIPTION
		"This shows the capacity of HDDs of server chassis."
	::= { chassisCapacity 6 }

chassisCapacityMediaDriveSlot            OBJECT-TYPE
	SYNTAX     Integer32
	MAX-ACCESS read-only
	STATUS     current
	DESCRIPTION
		"This shows the capacity of Peripheral drives of server chassis."
	::= { chassisCapacity 7 }

chassisCapacityFanModuleSlot             OBJECT-TYPE
	SYNTAX     Integer32
	MAX-ACCESS read-only
	STATUS     current
	DESCRIPTION
		"It shows the maximum number of slots for Fan modules."
	::= { chassisCapacity 8 }

chassisCapacityPowerSupplySlot           OBJECT-TYPE
	SYNTAX     Integer32
	MAX-ACCESS read-only
	STATUS     current
	DESCRIPTION
		"It shows the maximum number of slots for Power Supply modules."
	::= { chassisCapacity 9 }

chassisCapacityVoltageSensor             OBJECT-TYPE
	SYNTAX     Integer32
	MAX-ACCESS read-only
	STATUS     current
	DESCRIPTION
		"This shows the capacity of voltage sensors of chassis."
	::= { chassisCapacity 10 }

chassisCapacityTempSensor                OBJECT-TYPE
	SYNTAX     Integer32
	MAX-ACCESS read-only
	STATUS     current
	DESCRIPTION
		"This shows the capacity of temperature sensors of chassis."
	::= { chassisCapacity 11 }

chassisCapacityPhysicalPartition         OBJECT-TYPE
	SYNTAX     Integer32
	MAX-ACCESS read-only
	STATUS     current
	DESCRIPTION
		"This shows the capacity of physical partition of server chassis."
	::= { chassisCapacity 12 }

chassisSettings                          OBJECT IDENTIFIER ::= { chassis 3 }

chassisSettingsBelongPartitionNum        OBJECT-TYPE
	SYNTAX     Integer32
	MAX-ACCESS read-only
	STATUS     current
	DESCRIPTION
		"This shows the partition number of server chassis."
	::= { chassisSettings 1 }

chassisSettingsDetailHVMLicence          OBJECT-TYPE
	SYNTAX     DisplayString
	MAX-ACCESS read-only
	STATUS     current
	DESCRIPTION
		"This shows the HVM licence of detailed server chassis."
	::= { chassisSettings 2 }

chassisSettingsManagementPortIPAddress   OBJECT-TYPE
	SYNTAX     DisplayString
	MAX-ACCESS read-only
	STATUS     current
	DESCRIPTION
		"This shows the IP address of management port of server chassis."
	::= { chassisSettings 3 }

chassisSettingsPowerCapping              OBJECT-TYPE
	SYNTAX     INTEGER {
		invalid(1), PCAP(2), DCMI(3), unknown(4)
	}
	MAX-ACCESS read-only
	STATUS     current
	DESCRIPTION
		"This shows the power cap setting server chassis."
	::= { chassisSettings 4 }

chassisSettingsAddMAC                    OBJECT-TYPE
	SYNTAX     DisplayString
	MAX-ACCESS read-only
	STATUS     current
	DESCRIPTION
		"Reserved."
	::= { chassisSettings 5 }

chassisSettingsAddWWN                    OBJECT-TYPE
	SYNTAX     DisplayString
	MAX-ACCESS read-only
	STATUS     current
	DESCRIPTION
		"Reserved."
	::= { chassisSettings 6 }

chassisSettingsRackInfo                  OBJECT-TYPE
	SYNTAX     DisplayString
	MAX-ACCESS read-only
	STATUS     current
	DESCRIPTION
		"Reserved."
	::= { chassisSettings 7 }

chassisSettingsAssetTag                  OBJECT-TYPE
	SYNTAX     DisplayString
	MAX-ACCESS read-only
	STATUS     current
	DESCRIPTION
		"Reserved."
	::= { chassisSettings 8 }

chassisState                             OBJECT IDENTIFIER ::= { chassis 4 }

chassisStatePower                        OBJECT-TYPE
	SYNTAX     INTEGER {
		Poweroff(1), standby(2), PowerOn(3), unknown(4), Power-on-executing(5), Power-off-executing(6)
	}
	MAX-ACCESS read-only
	STATUS     current
	DESCRIPTION
		"This shows the power supply state of server chassis."
	::= { chassisState 1 }

chassisStateHealth                       OBJECT-TYPE
	SYNTAX     DisplayString
	MAX-ACCESS read-only
	STATUS     current
	DESCRIPTION
		"This shows the state of server chassis."
	::= { chassisState 2 }

chassisStateCurrentVoltage               OBJECT-TYPE
	SYNTAX     Integer32
	UNITS      "0.1 V"
	MAX-ACCESS read-only
	STATUS     current
	DESCRIPTION
		"This shows the current voltage of server chassis."
	::= { chassisState 3 }

chassisStateConsumptionCurrent           OBJECT-TYPE
	SYNTAX     Integer32
	UNITS      "0.1 A"
	MAX-ACCESS read-only
	STATUS     current
	DESCRIPTION
		"This shows the consumption current of server chassis."
	::= { chassisState 4 }

chassisStatePowerConsumption             OBJECT-TYPE
	SYNTAX     Integer32
	UNITS      "0.1 kW"
	MAX-ACCESS read-only
	STATUS     current
	DESCRIPTION
		"This shows the power consumption of server chassis."
	::= { chassisState 5 }

chassisStateIntakeTemp                   OBJECT-TYPE
	SYNTAX     Integer32
	UNITS      "0.1 degrees C"
	MAX-ACCESS read-only
	STATUS     current
	DESCRIPTION
		"This shows the state of intake temperature of server chassis."
	::= { chassisState 6 }

chassisStateFanAirVolume                 OBJECT-TYPE
	SYNTAX     Integer32
	UNITS      "0.1 m^3/min"
	MAX-ACCESS read-only
	STATUS     current
	DESCRIPTION
		"This shows the current air volume of fan module1."
	::= { chassisState 7 }

chassisRedundancy                        OBJECT IDENTIFIER ::= { chassisState 8 }

chassisRedundancyFan                     OBJECT-TYPE
	SYNTAX     INTEGER {
		redundancy(1), non-redundancy(2), unknown(3)
	}
	MAX-ACCESS read-only
	STATUS     current
	DESCRIPTION
		"This shows the redundancy of fan module of server chassis."
	::= { chassisRedundancy 1 }

chassisRedundancyPowerSupply             OBJECT-TYPE
	SYNTAX     INTEGER {
		redundancy(1), non-redundancy(2), unknown(3)
	}
	MAX-ACCESS read-only
	STATUS     current
	DESCRIPTION
		"This shows the redundancy of power supply module of server chassis."
	::= { chassisRedundancy 2 }

chassisFrontPanelLEDTable                OBJECT-TYPE
	SYNTAX SEQUENCE OF chassisFrontPanelLEDEntry
	MAX-ACCESS not-accessible
	STATUS     current
	DESCRIPTION
		"This shows the table of front panel LED of server chassis."
	::= { chassisState 9 }

chassisFrontPanelLEDEntry                OBJECT-TYPE
	SYNTAX     ChassisFrontPanelLEDEntry
	MAX-ACCESS not-accessible
	STATUS     current
	DESCRIPTION
		"This shows the entry of front panel LED of server chassis."
	INDEX { chassisFrontPanelLEDIndex }
	::= { chassisFrontPanelLEDTable 1 }

ChassisFrontPanelLEDEntry ::= SEQUENCE {
	chassisFrontPanelLEDIndex
		Integer32,
	chassisFrontPanelLEDName
		DisplayString,
	chassisFrontPanelLEDType
		DisplayString,
	chassisFrontPanelLEDState
		INTEGER,
	chassisFrontPanelLEDColor
		INTEGER
}

chassisFrontPanelLEDIndex                OBJECT-TYPE
	SYNTAX     Integer32
	MAX-ACCESS read-only
	STATUS     current
	DESCRIPTION
		"This shows the index of front panel LED of server chassis."
	::= { chassisFrontPanelLEDEntry 1 }

chassisFrontPanelLEDName                 OBJECT-TYPE
	SYNTAX     DisplayString
	MAX-ACCESS read-only
	STATUS     current
	DESCRIPTION
		"This shows the name of front panel LED of server chassis."
	::= { chassisFrontPanelLEDEntry 2 }

chassisFrontPanelLEDType                 OBJECT-TYPE
	SYNTAX     DisplayString
	MAX-ACCESS read-only
	STATUS     current
	DESCRIPTION
		"Reserved."
	::= { chassisFrontPanelLEDEntry 3 }

chassisFrontPanelLEDState                OBJECT-TYPE
	SYNTAX     INTEGER {
		turn-off(1), turn-on(2), unknown(3), blink(4), blink-fast(5), blink-slow(6)
	}
	MAX-ACCESS read-only
	STATUS     current
	DESCRIPTION
		"This shows the state of front panel LED of server chassis."
	::= { chassisFrontPanelLEDEntry 4 }

chassisFrontPanelLEDColor                OBJECT-TYPE
	SYNTAX     INTEGER {
		blue(1), green(2), red(3), amber(4), unknown(5)
	}
	MAX-ACCESS read-only
	STATUS     current
	DESCRIPTION
		"This shows the color of front panel LED of server chassis."
	::= { chassisFrontPanelLEDEntry 5 }

chassisPostCodeLED                       OBJECT-TYPE
	SYNTAX     Integer32
	MAX-ACCESS read-only
	STATUS     current
	DESCRIPTION
		"This shows the post code of front panel seven segment LED of server chassis."
	::= { chassisState 10 }

chassisStateOther                        OBJECT IDENTIFIER ::= { chassisState 20 }

chassisMaintMode                         OBJECT-TYPE
	SYNTAX     INTEGER {
		Normal(1), CE-Maint-mode(2), User-Maint-mode(3), unknown(4)
	}
	MAX-ACCESS read-only
	STATUS     current
	DESCRIPTION
		"This shows the maintenance mode of server chassis."
	::= { chassisStateOther 1 }

chassisLatestHWLogInfo                   OBJECT-TYPE
	SYNTAX     DisplayString
	MAX-ACCESS read-only
	STATUS     current
	DESCRIPTION
		"This shows the information on the newest HW logs of server chassis."
	::= { chassisState 30 }

chassisHWLogTable                        OBJECT-TYPE
	SYNTAX SEQUENCE OF chassisHWLogEntry
	MAX-ACCESS not-accessible
	STATUS     current
	DESCRIPTION
		"This shows the table on the hardware logs of server chassis."
	::= { chassisState 31 }

chassisHWLogEntry                        OBJECT-TYPE
	SYNTAX     ChassisHWLogEntry
	MAX-ACCESS not-accessible
	STATUS     current
	DESCRIPTION
		"This shows the table on the hardware logs of server chassis."
	INDEX { chassisHWLogIndex }
	::= { chassisHWLogTable 1 }

ChassisHWLogEntry ::= SEQUENCE {
	chassisHWLogIndex
		Integer32,
	chassisHWLogExist
		INTEGER,
	chassisHWLogGenerateID
		DisplayString,
	chassisHWLogRecordID
		DisplayString,
	chassisHWLogDate
		DisplayString,
	chassisHWLogCode
		DisplayString,
	chassisHWLogDetail
		DisplayString
}

chassisHWLogIndex                        OBJECT-TYPE
	SYNTAX     Integer32
	MAX-ACCESS read-only
	STATUS     current
	DESCRIPTION
		"This shows the index on the hardware logs of server chassis."
	::= { chassisHWLogEntry 1 }

chassisHWLogExist                        OBJECT-TYPE
	SYNTAX     INTEGER {
		not-exist(1), exist(2), unknown(3)
	}
	MAX-ACCESS read-only
	STATUS     current
	DESCRIPTION
		"This shows the registrated state on the hardware logs of server chassis."
	::= { chassisHWLogEntry 2 }

chassisHWLogGenerateID                   OBJECT-TYPE
	SYNTAX     DisplayString
	MAX-ACCESS read-only
	STATUS     current
	DESCRIPTION
		"This shows the occurred part on the hardware logs of server chassis."
	::= { chassisHWLogEntry 3 }

chassisHWLogRecordID                     OBJECT-TYPE
	SYNTAX     DisplayString
	MAX-ACCESS read-only
	STATUS     current
	DESCRIPTION
		"This shows the recorded ID on the hardware logs of server chassis."
	::= { chassisHWLogEntry 4 }

chassisHWLogDate                         OBJECT-TYPE
	SYNTAX     DisplayString
	MAX-ACCESS read-only
	STATUS     current
	DESCRIPTION
		"This shows the occurred date and time on the hardware logs of server chassis."
	::= { chassisHWLogEntry 5 }

chassisHWLogCode                         OBJECT-TYPE
	SYNTAX     DisplayString
	MAX-ACCESS read-only
	STATUS     current
	DESCRIPTION
		"This shows the occurred event code on the hardware logs of server chassis."
	::= { chassisHWLogEntry 6 }

chassisHWLogDetail                       OBJECT-TYPE
	SYNTAX     DisplayString
	MAX-ACCESS read-only
	STATUS     current
	DESCRIPTION
		"This shows the occurred event detail on the hardware logs of server chassis."
	::= { chassisHWLogEntry 7 }

chassisInstall                           OBJECT IDENTIFIER ::= { chassisState 40 }

chassisInsFrontPanel                     OBJECT-TYPE
	SYNTAX     INTEGER {
		non-exist(1), exist(2), unknown(3)
	}
	MAX-ACCESS read-only
	STATUS     current
	DESCRIPTION
		"This shows the installed state of front panel of server chassis."
	::= { chassisInstall 1 }

chassisInsCPUSocketTable                 OBJECT-TYPE
	SYNTAX SEQUENCE OF chassisInsCPUSocketEntry
	MAX-ACCESS not-accessible
	STATUS     current
	DESCRIPTION
		"This shows the table of CPU socket of server chassis."
	::= { chassisInstall 2 }

chassisInsCPUSocketEntry                 OBJECT-TYPE
	SYNTAX     ChassisInsCPUSocketEntry
	MAX-ACCESS not-accessible
	STATUS     current
	DESCRIPTION
		"This shows the entry of CPU socket of server chassis."
	INDEX { chassisInsCPUSocketIndex }
	::= { chassisInsCPUSocketTable 1 }

ChassisInsCPUSocketEntry ::= SEQUENCE {
	chassisInsCPUSocketIndex
		Integer32,
	chassisInsCPUSocketNum
		Integer32,
	chassisInsCPUSocketExist
		INTEGER,
	chassisInsCPUSocketCPUName
		DisplayString,
	chassisInsCPUSocketCPUFrequency
		Integer32,
	chassisInsCPUSocketCPUStepping
		DisplayString,
	chassisInsCPUSocketCPUCoreNum
		Integer32,
	chassisInsCPUSocketCPUUpperLimitTemp
		Integer32,
	chassisInsCPUSocketCPULowerLimitTemp
		Integer32
}

chassisInsCPUSocketIndex                 OBJECT-TYPE
	SYNTAX     Integer32
	MAX-ACCESS read-only
	STATUS     current
	DESCRIPTION
		"This shows the index of CPU socket of server chassis."
	::= { chassisInsCPUSocketEntry 1 }

chassisInsCPUSocketNum                   OBJECT-TYPE
	SYNTAX     Integer32
	MAX-ACCESS read-only
	STATUS     current
	DESCRIPTION
		"This shows the number of CPU sockets of server chassis."
	::= { chassisInsCPUSocketEntry 2 }

chassisInsCPUSocketExist                 OBJECT-TYPE
	SYNTAX     INTEGER {
		non-exist(1), exist(2), unknown(3)
	}
	MAX-ACCESS read-only
	STATUS     current
	DESCRIPTION
		"This shows the registrated state of CPU socket of server chassis."
	::= { chassisInsCPUSocketEntry 3 }

chassisInsCPUSocketCPUName               OBJECT-TYPE
	SYNTAX     DisplayString
	MAX-ACCESS read-only
	STATUS     current
	DESCRIPTION
		"This shows the CPU name of CPU socket of server chassis."
	::= { chassisInsCPUSocketEntry 4 }

chassisInsCPUSocketCPUFrequency          OBJECT-TYPE
	SYNTAX     Integer32
	UNITS      "MHz"
	MAX-ACCESS read-only
	STATUS     current
	DESCRIPTION
		"This shows the CPU frequency of CPU socket of server chassis."
	::= { chassisInsCPUSocketEntry 5 }

chassisInsCPUSocketCPUStepping           OBJECT-TYPE
	SYNTAX     DisplayString
	MAX-ACCESS read-only
	STATUS     current
	DESCRIPTION
		"This shows the CPU stepping of CPU socket of server chassis."
	::= { chassisInsCPUSocketEntry 6 }

chassisInsCPUSocketCPUCoreNum            OBJECT-TYPE
	SYNTAX     Integer32
	MAX-ACCESS read-only
	STATUS     current
	DESCRIPTION
		"This shows the CPU core number of CPU socket of server chassis."
	::= { chassisInsCPUSocketEntry 7 }

chassisInsCPUSocketCPUUpperLimitTemp     OBJECT-TYPE
	SYNTAX     Integer32
	UNITS      "0.1 degrees C"
	MAX-ACCESS read-only
	STATUS     current
	DESCRIPTION
		"This shows the highest temperature threshold of CPU0 sensor in server chassis."
	::= { chassisInsCPUSocketEntry 8 }

chassisInsCPUSocketCPULowerLimitTemp     OBJECT-TYPE
	SYNTAX     Integer32
	UNITS      "0.1 degrees C"
	MAX-ACCESS read-only
	STATUS     current
	DESCRIPTION
		"This shows the lowest temperature threshold of CPU0 sensor in server chassis."
	::= { chassisInsCPUSocketEntry 9 }

chassisInsDIMMCapacity                   OBJECT-TYPE
	SYNTAX     Integer32
	UNITS      "GB"
	MAX-ACCESS read-only
	STATUS     current
	DESCRIPTION
		"This shows the total amount of DIMM capacity of server chassis."
	::= { chassisInstall 3 }

chassisInsDIMMSlotTable                  OBJECT-TYPE
	SYNTAX SEQUENCE OF chassisInsDIMMSlotEntry
	MAX-ACCESS not-accessible
	STATUS     current
	DESCRIPTION
		"This shows the table of DIMM slot of server chassis."
	::= { chassisInstall 4 }

chassisInsDIMMSlotEntry                  OBJECT-TYPE
	SYNTAX     ChassisInsDIMMSlotEntry
	MAX-ACCESS not-accessible
	STATUS     current
	DESCRIPTION
		"This shows the entry of DIMM slot of server chassis."
	INDEX { chassisInsDIMMSlotIndex }
	::= { chassisInsDIMMSlotTable 1 }

ChassisInsDIMMSlotEntry ::= SEQUENCE {
	chassisInsDIMMSlotIndex
		Integer32,
	chassisInsDIMMSlotNum
		Integer32,
	chassisInsDIMMSlotExist
		INTEGER,
	chassisInsDIMMSlotDIMMCapacity
		Integer32,
	chassisInsDIMMSlotDIMMType
		DisplayString,
	chassisInsDIMMSlotDIMMFrequency
		Integer32,
	chassisInsDIMMSlotDIMMCasLatency
		INTEGER,
	chassisInsDIMMSlotDIMMStatus
		INTEGER
}

chassisInsDIMMSlotIndex                  OBJECT-TYPE
	SYNTAX     Integer32
	MAX-ACCESS read-only
	STATUS     current
	DESCRIPTION
		"This shows the index of DIMM slot of server chassis."
	::= { chassisInsDIMMSlotEntry 1 }

chassisInsDIMMSlotNum                    OBJECT-TYPE
	SYNTAX     Integer32
	MAX-ACCESS read-only
	STATUS     current
	DESCRIPTION
		"This shows the registrated state of DIMM slot of server chassis."
	::= { chassisInsDIMMSlotEntry 2 }

chassisInsDIMMSlotExist                  OBJECT-TYPE
	SYNTAX     INTEGER {
		non-exist(1), exist(2), unknown(3)
	}
	MAX-ACCESS read-only
	STATUS     current
	DESCRIPTION
		"This shows the capacity of DIMM slots of server chassis."
	::= { chassisInsDIMMSlotEntry 3 }

chassisInsDIMMSlotDIMMCapacity           OBJECT-TYPE
	SYNTAX     Integer32
	UNITS      "GB"
	MAX-ACCESS read-only
	STATUS     current
	DESCRIPTION
		"This shows the DIMM type of DIMM slot of server chassis."
	::= { chassisInsDIMMSlotEntry 4 }

chassisInsDIMMSlotDIMMType               OBJECT-TYPE
	SYNTAX     DisplayString
	MAX-ACCESS read-only
	STATUS     current
	DESCRIPTION
		"This shows the DIMM frequency of DIMM slot of server chassis."
	::= { chassisInsDIMMSlotEntry 5 }

chassisInsDIMMSlotDIMMFrequency          OBJECT-TYPE
	SYNTAX     Integer32
	UNITS      "MHz"
	MAX-ACCESS read-only
	STATUS     current
	DESCRIPTION
		"This shows the DIMM cas latency of DIMM slot of server chassis."
	::= { chassisInsDIMMSlotEntry 6 }

chassisInsDIMMSlotDIMMCasLatency         OBJECT-TYPE
	SYNTAX     INTEGER {
		normal(1), unknown(2), degenerated(3), planned-degenerated(4)
	}
	MAX-ACCESS read-only
	STATUS     current
	DESCRIPTION
		"This shows the DIMM state of DIMM slot of server chassis."
	::= { chassisInsDIMMSlotEntry 7 }

chassisInsDIMMSlotDIMMStatus             OBJECT-TYPE
	SYNTAX     INTEGER {
		normal(1), unknown(2), degenerated(3), planned-degenerated(4)
	}
	MAX-ACCESS read-only
	STATUS     current
	DESCRIPTION
		"This shows the DIMM state of DIMM slot of server chassis."
	::= { chassisInsDIMMSlotEntry 8 }

chassisInsPCISlotTable                   OBJECT-TYPE
	SYNTAX SEQUENCE OF chassisInsPCISlotEntry
	MAX-ACCESS not-accessible
	STATUS     current
	DESCRIPTION
		"This shows the table of PCI slot of server chassis."
	::= { chassisInstall 5 }

chassisInsPCISlotEntry                   OBJECT-TYPE
	SYNTAX     ChassisInsPCISlotEntry
	MAX-ACCESS not-accessible
	STATUS     current
	DESCRIPTION
		"This shows the entry of PCI slot of server chassis."
	INDEX { chassisInsPCISlotIndex }
	::= { chassisInsPCISlotTable 1 }

ChassisInsPCISlotEntry ::= SEQUENCE {
	chassisInsPCISlotIndex
		Integer32,
	chassisInsPCISlotNum
		Integer32,
	chassisInsPCISlotType
		DisplayString,
	chassisInsPCISlotExist
		INTEGER,
	chassisInsPCISlotPCIType
		DisplayString,
	chassisInsPCISlotPCIProductName
		DisplayString,
	chassisInsPCISlotPCISerial
		DisplayString,
	chassisInsPCISlotPCIManufacturer
		DisplayString
}

chassisInsPCISlotIndex                   OBJECT-TYPE
	SYNTAX     Integer32
	MAX-ACCESS read-only
	STATUS     current
	DESCRIPTION
		"This shows the index of PCI slot of server chassis."
	::= { chassisInsPCISlotEntry 1 }

chassisInsPCISlotNum                     OBJECT-TYPE
	SYNTAX     Integer32
	MAX-ACCESS read-only
	STATUS     current
	DESCRIPTION
		"This shows the slot number of PCI slot of server chassis."
	::= { chassisInsPCISlotEntry 2 }

chassisInsPCISlotType                    OBJECT-TYPE
	SYNTAX     DisplayString
	MAX-ACCESS read-only
	STATUS     current
	DESCRIPTION
		"This shows the type of PCI slot of server chassis."
	::= { chassisInsPCISlotEntry 3 }

chassisInsPCISlotExist                   OBJECT-TYPE
	SYNTAX     INTEGER {
		non-exist(1), exist(2), unknown(3)
	}
	MAX-ACCESS read-only
	STATUS     current
	DESCRIPTION
		"This shows the registrated state of PCI slot of server chassis."
	::= { chassisInsPCISlotEntry 4 }

chassisInsPCISlotPCIType                 OBJECT-TYPE
	SYNTAX     DisplayString
	MAX-ACCESS read-only
	STATUS     current
	DESCRIPTION
		"This shows the PCI type of PCI slot of server chassis."
	::= { chassisInsPCISlotEntry 5 }

chassisInsPCISlotPCIProductName          OBJECT-TYPE
	SYNTAX     DisplayString
	MAX-ACCESS read-only
	STATUS     current
	DESCRIPTION
		"This shows the PCI product name of PCI slot of server chassis."
	::= { chassisInsPCISlotEntry 6 }

chassisInsPCISlotPCISerial               OBJECT-TYPE
	SYNTAX     DisplayString
	MAX-ACCESS read-only
	STATUS     current
	DESCRIPTION
		"This shows the serial number of PCI slot of server chassis."
	::= { chassisInsPCISlotEntry 7 }

chassisInsPCISlotPCIManufacturer         OBJECT-TYPE
	SYNTAX     DisplayString
	MAX-ACCESS read-only
	STATUS     current
	DESCRIPTION
		"This shows the manufacturer of PCI slot of server chassis."
	::= { chassisInsPCISlotEntry 8 }

chassisInsLOMTable                       OBJECT-TYPE
	SYNTAX SEQUENCE OF chassisInsLOMEntry
	MAX-ACCESS not-accessible
	STATUS     current
	DESCRIPTION
		"This shows the table of onboard LAN of server chassis."
	::= { chassisInstall 6 }

chassisInsLOMEntry                       OBJECT-TYPE
	SYNTAX     ChassisInsLOMEntry
	MAX-ACCESS not-accessible
	STATUS     current
	DESCRIPTION
		"This shows the entry of onboard LAN of server chassis."
	INDEX { chassisInsLOMIndex }
	::= { chassisInsLOMTable 1 }

ChassisInsLOMEntry ::= SEQUENCE {
	chassisInsLOMIndex
		Integer32,
	chassisInsLOMType
		DisplayString,
	chassisInsLOMLinkSpeed
		Integer32,
	chassisInsLOMMAC
		DisplayString,
	chassisInsLOMLinkStatus
		INTEGER,
	chassisInsLOMPortDivide
		INTEGER,
	chassisInsLOMPortDivideNum
		Integer32
}

chassisInsLOMIndex                       OBJECT-TYPE
	SYNTAX     Integer32
	MAX-ACCESS read-only
	STATUS     current
	DESCRIPTION
		"This shows the index of onboard LAN of server chassis."
	::= { chassisInsLOMEntry 1 }

chassisInsLOMType                        OBJECT-TYPE
	SYNTAX     DisplayString
	MAX-ACCESS read-only
	STATUS     current
	DESCRIPTION
		"This shows the type of onboard LAN of server chassis."
	::= { chassisInsLOMEntry 2 }

chassisInsLOMLinkSpeed                   OBJECT-TYPE
	SYNTAX     Integer32
	MAX-ACCESS read-only
	STATUS     current
	DESCRIPTION
		"This shows the link speed of onboard LAN of server chassis."
	::= { chassisInsLOMEntry 3 }

chassisInsLOMMAC                         OBJECT-TYPE
	SYNTAX     DisplayString
	MAX-ACCESS read-only
	STATUS     current
	DESCRIPTION
		"This shows the MAC address of onboard LAN of server chassis."
	::= { chassisInsLOMEntry 4 }

chassisInsLOMLinkStatus                  OBJECT-TYPE
	SYNTAX     INTEGER {
		up(1), down(2), unknown(3)
	}
	MAX-ACCESS read-only
	STATUS     current
	DESCRIPTION
		"This shows the link state of onboard LAN of server chassis."
	::= { chassisInsLOMEntry 5 }

chassisInsLOMPortDivide                  OBJECT-TYPE
	SYNTAX     INTEGER {
		possible(1), Impossible(2), unknown(3)
	}
	MAX-ACCESS read-only
	STATUS     current
	DESCRIPTION
		"This shows the port divide propriety of onboard LAN of server chassis."
	::= { chassisInsLOMEntry 6 }

chassisInsLOMPortDivideNum               OBJECT-TYPE
	SYNTAX     Integer32
	MAX-ACCESS read-only
	STATUS     current
	DESCRIPTION
		"This shows the port divide number of onboard LAN of server chassis."
	::= { chassisInsLOMEntry 7 }

chassisInsFanTable                       OBJECT-TYPE
	SYNTAX SEQUENCE OF chassisInsFanEntry
	MAX-ACCESS not-accessible
	STATUS     current
	DESCRIPTION
		"This shows the table of fan of server chassis."
	::= { chassisInstall 7 }

chassisInsFanEntry                       OBJECT-TYPE
	SYNTAX     ChassisInsFanEntry
	MAX-ACCESS not-accessible
	STATUS     current
	DESCRIPTION
		"This shows the entry of fan of server chassis."
	INDEX { chassisInsFanIndex }
	::= { chassisInsFanTable 1 }

ChassisInsFanEntry ::= SEQUENCE {
	chassisInsFanIndex
		Integer32,
	chassisInsFanLocation
		DisplayString,
	chassisInsFanExist
		INTEGER,
	chassisInsFanMaxRPM
		Integer32,
	chassisInsFanMaxAirVolume
		Integer32,
	chassisInsFanRPM
		Integer32,
	chassisInsFanAirVolume
		Integer32,
	chassisInsFanRPMValid
		INTEGER,
	chassisInsFanStateHealth
		INTEGER
}

chassisInsFanIndex                       OBJECT-TYPE
	SYNTAX     Integer32
	MAX-ACCESS read-only
	STATUS     current
	DESCRIPTION
		"This shows the index of fan of server chassis."
	::= { chassisInsFanEntry 1 }

chassisInsFanLocation                    OBJECT-TYPE
	SYNTAX     DisplayString
	MAX-ACCESS read-only
	STATUS     current
	DESCRIPTION
		"This shows the location of fan of server chassis."
	::= { chassisInsFanEntry 2 }

chassisInsFanExist                       OBJECT-TYPE
	SYNTAX     INTEGER {
		non-exist(1), exist(2), unknown(3)
	}
	MAX-ACCESS read-only
	STATUS     current
	DESCRIPTION
		"This shows the registrated state of fan."
	::= { chassisInsFanEntry 3 }

chassisInsFanMaxRPM                      OBJECT-TYPE
	SYNTAX     Integer32
	UNITS      "rpm"
	MAX-ACCESS read-only
	STATUS     current
	DESCRIPTION
		"This shows the maximum rpm of fan."
	::= { chassisInsFanEntry 4 }

chassisInsFanMaxAirVolume                OBJECT-TYPE
	SYNTAX     Integer32
	UNITS      "0.1 m^3/min"
	MAX-ACCESS read-only
	STATUS     current
	DESCRIPTION
		"This shows the maximum air volume of fan."
	::= { chassisInsFanEntry 5 }

chassisInsFanRPM                         OBJECT-TYPE
	SYNTAX     Integer32
	UNITS      "rpm"
	MAX-ACCESS read-only
	STATUS     current
	DESCRIPTION
		"This shows the rpm value of fan."
	::= { chassisInsFanEntry 6 }

chassisInsFanAirVolume                   OBJECT-TYPE
	SYNTAX     Integer32
	UNITS      "0.1 m^3/min"
	MAX-ACCESS read-only
	STATUS     current
	DESCRIPTION
		"This shows the air volume of fan."
	::= { chassisInsFanEntry 7 }

chassisInsFanRPMValid                    OBJECT-TYPE
	SYNTAX     INTEGER {
		invalid(1), valid(2), unknown(3)
	}
	MAX-ACCESS read-only
	STATUS     current
	DESCRIPTION
		"This shows the validity of fan rpm value of fan."
	::= { chassisInsFanEntry 8 }

chassisInsFanStateHealth                 OBJECT-TYPE
	SYNTAX     INTEGER {
		normal(1), fail(2), unknown(3)
	}
	MAX-ACCESS read-only
	STATUS     current
	DESCRIPTION
		"This shows the health state of fan."
	::= { chassisInsFanEntry 9 }

chassisHDDSlotTable                      OBJECT-TYPE
	SYNTAX SEQUENCE OF chassisHDDSlotEntry
	MAX-ACCESS not-accessible
	STATUS     current
	DESCRIPTION
		"This shows the table of HDD slot of server chassis."
	::= { chassisInstall 8 }

chassisHDDSlotEntry                      OBJECT-TYPE
	SYNTAX     ChassisHDDSlotEntry
	MAX-ACCESS not-accessible
	STATUS     current
	DESCRIPTION
		"This shows the entry of HDD slot of server chassis."
	INDEX { chassisHDDSlotIndex }
	::= { chassisHDDSlotTable 1 }

ChassisHDDSlotEntry ::= SEQUENCE {
	chassisHDDSlotIndex
		Integer32,
	chassisHDDSlot1Num
		Integer32,
	chassisHDDSlot1Exist
		INTEGER,
	chassisHDDSlot1HDDType
		DisplayString,
	chassisHDDSlot1HDDProductName
		DisplayString,
	chassisHDDSlot1HDDModel
		DisplayString,
	chassisHDDSlot1HDDSerialNum
		DisplayString,
	chassisHDDSlot1HDDCapacity
		Integer32,
	chassisHDDSlot1HDDRPM
		Integer32,
	chassisHDDSlot1HDDStatePower
		INTEGER,
	chassisHDDSlot1HDDStateHealth
		INTEGER,
	chassisHDDSlot1HDDStateLEDACT
		INTEGER,
	chassisHDDSlot1HDDStateLEDSTS
		INTEGER,
	chassisHDDSlot1HDDFWInfo1Name
		DisplayString,
	chassisHDDSlot1HDDFWInfo1CurrentVer
		DisplayString,
	chassisHDDSlot1HDDFWInfo1NextVer
		DisplayString
}

chassisHDDSlotIndex                      OBJECT-TYPE
	SYNTAX     Integer32
	MAX-ACCESS read-only
	STATUS     current
	DESCRIPTION
		"This shows the index of HDD slot of server chassis."
	::= { chassisHDDSlotEntry 1 }

chassisHDDSlot1Num                       OBJECT-TYPE
	SYNTAX     Integer32
	MAX-ACCESS read-only
	STATUS     current
	DESCRIPTION
		"This shows the number of HDD slots of server chassis."
	::= { chassisHDDSlotEntry 2 }

chassisHDDSlot1Exist                     OBJECT-TYPE
	SYNTAX     INTEGER {
		non-exist(1), exist(2), unknown(3)
	}
	MAX-ACCESS read-only
	STATUS     current
	DESCRIPTION
		"This shows the registrated state of HDD slot of server chassis."
	::= { chassisHDDSlotEntry 3 }

chassisHDDSlot1HDDType                   OBJECT-TYPE
	SYNTAX     DisplayString
	MAX-ACCESS read-only
	STATUS     current
	DESCRIPTION
		"This shows the HDD type of HDD slot of server chassis."
	::= { chassisHDDSlotEntry 4 }

chassisHDDSlot1HDDProductName            OBJECT-TYPE
	SYNTAX     DisplayString
	MAX-ACCESS read-only
	STATUS     current
	DESCRIPTION
		"This shows the HDD product name of HDD slot of server chassis."
	::= { chassisHDDSlotEntry 5 }

chassisHDDSlot1HDDModel                  OBJECT-TYPE
	SYNTAX     DisplayString
	MAX-ACCESS read-only
	STATUS     current
	DESCRIPTION
		"This shows the HDD model of HDD slot of server chassis."
	::= { chassisHDDSlotEntry 6 }

chassisHDDSlot1HDDSerialNum              OBJECT-TYPE
	SYNTAX     DisplayString
	MAX-ACCESS read-only
	STATUS     current
	DESCRIPTION
		"This shows the HDD serial number of HDD slot of server chassis."
	::= { chassisHDDSlotEntry 7 }

chassisHDDSlot1HDDCapacity               OBJECT-TYPE
	SYNTAX     Integer32
	UNITS      "GB"
	MAX-ACCESS read-only
	STATUS     current
	DESCRIPTION
		"This shows the HDD capacity of HDD slots of server chassis."
	::= { chassisHDDSlotEntry 8 }

chassisHDDSlot1HDDRPM                    OBJECT-TYPE
	SYNTAX     Integer32
	UNITS      "rpm"
	MAX-ACCESS read-only
	STATUS     current
	DESCRIPTION
		"This shows the HDD drive speed of HDD slot of server chassis."
	::= { chassisHDDSlotEntry 9 }

chassisHDDSlot1HDDStatePower             OBJECT-TYPE
	SYNTAX     INTEGER {
		poweroff(1), poweron(2), unknown(3)
	}
	MAX-ACCESS read-only
	STATUS     current
	DESCRIPTION
		"This shows the HDD power supply state of HDD slot of server chassis."
	::= { chassisHDDSlotEntry 10 }

chassisHDDSlot1HDDStateHealth            OBJECT-TYPE
	SYNTAX     INTEGER {
		normal(1), fail(2), unknown(3)
	}
	MAX-ACCESS read-only
	STATUS     current
	DESCRIPTION
		"This shows the HDD health state of HDD slot of server chassis."
	::= { chassisHDDSlotEntry 11 }

chassisHDDSlot1HDDStateLEDACT            OBJECT-TYPE
	SYNTAX     INTEGER {
		turn-off(1), turn-on(2), unknown(3), blink(4), blink-fast(5), blink-slow(6)
	}
	MAX-ACCESS read-only
	STATUS     current
	DESCRIPTION
		"This shows the LED state of HDD slot of server chassis(activity)."
	::= { chassisHDDSlotEntry 12 }

chassisHDDSlot1HDDStateLEDSTS            OBJECT-TYPE
	SYNTAX     INTEGER {
		turn-off(1), turn-on(2), unknown(3), blink(4), blink-fast(5), blink-slow(6)
	}
	MAX-ACCESS read-only
	STATUS     current
	DESCRIPTION
		"This shows the LED state of HDD slot of server chassis(status)."
	::= { chassisHDDSlotEntry 13 }

chassisHDDSlot1HDDFWInfo1Name            OBJECT-TYPE
	SYNTAX     DisplayString
	MAX-ACCESS read-only
	STATUS     current
	DESCRIPTION
		"This shows the HDD firmware name of HDD slot of server chassis."
	::= { chassisHDDSlotEntry 20 }

chassisHDDSlot1HDDFWInfo1CurrentVer      OBJECT-TYPE
	SYNTAX     DisplayString
	MAX-ACCESS read-only
	STATUS     current
	DESCRIPTION
		"This shows the HDD firmware current version of HDD slot of server chassis."
	::= { chassisHDDSlotEntry 21 }

chassisHDDSlot1HDDFWInfo1NextVer         OBJECT-TYPE
	SYNTAX     DisplayString
	MAX-ACCESS read-only
	STATUS     current
	DESCRIPTION
		"This shows the HDD firmware next version of HDD slot of server chassis."
	::= { chassisHDDSlotEntry 22 }

chassisMediaDriveSlotTable               OBJECT-TYPE
	SYNTAX SEQUENCE OF chassisMediaDriveSlotEntry
	MAX-ACCESS not-accessible
	STATUS     current
	DESCRIPTION
		"This shows the table of Peripheral drive slot of server chassis."
	::= { chassisInstall 9 }

chassisMediaDriveSlotEntry               OBJECT-TYPE
	SYNTAX     ChassisMediaDriveSlotEntry
	MAX-ACCESS not-accessible
	STATUS     current
	DESCRIPTION
		"This shows the entry of Peripheral drive slot of server chassis."
	INDEX { chassisMediaDriveSlotIndex }
	::= { chassisMediaDriveSlotTable 1 }

ChassisMediaDriveSlotEntry ::= SEQUENCE {
	chassisMediaDriveSlotIndex
		Integer32,
	chassisMediaDriveSlotNum
		Integer32,
	chassisMediaDriveSlotExist
		INTEGER,
	chassisMediaDriveSlotDriveType
		DisplayString,
	chassisMediaDriveSlotDriveProductName
		DisplayString,
	chassisMediaDriveSlotDriveModel
		DisplayString,
	chassisMediaDriveSlotDriveSerialNum
		DisplayString,
	chassisMediaDriveSlotDriveStatePower
		INTEGER,
	chassisMediaDriveSlotDriveStateHealth
		INTEGER
}

chassisMediaDriveSlotIndex               OBJECT-TYPE
	SYNTAX     Integer32
	MAX-ACCESS read-only
	STATUS     current
	DESCRIPTION
		"This shows the index of Peripheral drive slot of server chassis."
	::= { chassisMediaDriveSlotEntry 1 }

chassisMediaDriveSlotNum                 OBJECT-TYPE
	SYNTAX     Integer32
	MAX-ACCESS read-only
	STATUS     current
	DESCRIPTION
		"This shows the number of Peripheral drive slots of server chassis."
	::= { chassisMediaDriveSlotEntry 2 }

chassisMediaDriveSlotExist               OBJECT-TYPE
	SYNTAX     INTEGER {
		non-exist(1), exist(2), unknown(3)
	}
	MAX-ACCESS read-only
	STATUS     current
	DESCRIPTION
		"This shows the registrated state of Peripheral drive slot of server chassis."
	::= { chassisMediaDriveSlotEntry 3 }

chassisMediaDriveSlotDriveType           OBJECT-TYPE
	SYNTAX     DisplayString
	MAX-ACCESS read-only
	STATUS     current
	DESCRIPTION
		"This shows the HDD type of Peripheral drive slot of server chassis."
	::= { chassisMediaDriveSlotEntry 4 }

chassisMediaDriveSlotDriveProductName    OBJECT-TYPE
	SYNTAX     DisplayString
	MAX-ACCESS read-only
	STATUS     current
	DESCRIPTION
		"This shows the HDD product name of Peripheral drive slot of server chassis."
	::= { chassisMediaDriveSlotEntry 5 }

chassisMediaDriveSlotDriveModel          OBJECT-TYPE
	SYNTAX     DisplayString
	MAX-ACCESS read-only
	STATUS     current
	DESCRIPTION
		"This shows the HDD model of Peripheral drive slot of server chassis."
	::= { chassisMediaDriveSlotEntry 6 }

chassisMediaDriveSlotDriveSerialNum      OBJECT-TYPE
	SYNTAX     DisplayString
	MAX-ACCESS read-only
	STATUS     current
	DESCRIPTION
		"This shows the HDD serial number of Peripheral drive slot of server chassis."
	::= { chassisMediaDriveSlotEntry 7 }

chassisMediaDriveSlotDriveStatePower     OBJECT-TYPE
	SYNTAX     INTEGER {
		poweroff(1), poweron(2), unknown(3)
	}
	MAX-ACCESS read-only
	STATUS     current
	DESCRIPTION
		"This shows the Peripheral drive power supply state of Peripheral drive slot of server chassis."
	::= { chassisMediaDriveSlotEntry 10 }

chassisMediaDriveSlotDriveStateHealth    OBJECT-TYPE
	SYNTAX     INTEGER {
		normal(1), fail(2), unknown(3)
	}
	MAX-ACCESS read-only
	STATUS     current
	DESCRIPTION
		"This shows the Peripheral drive health state of Peripheral drive slot of server chassis."
	::= { chassisMediaDriveSlotEntry 11 }

chassisInsFanSlotTable                   OBJECT-TYPE
	SYNTAX SEQUENCE OF chassisInsFanSlotEntry
	MAX-ACCESS not-accessible
	STATUS     current
	DESCRIPTION
		"This shows the table of fan module slot of server chassis."
	::= { chassisInstall 10 }

chassisInsFanSlotEntry                   OBJECT-TYPE
	SYNTAX     ChassisInsFanSlotEntry
	MAX-ACCESS not-accessible
	STATUS     current
	DESCRIPTION
		"This shows the entry of fan module slot of server chassis."
	INDEX { chassisInsFanSlotIndex }
	::= { chassisInsFanSlotTable 1 }

ChassisInsFanSlotEntry ::= SEQUENCE {
	chassisInsFanSlotIndex
		Integer32,
	chassisInsFanSlotNum
		Integer32,
	chassisInsFanSlotExist
		INTEGER,
	chassisInsFanSlotObjectID
		OBJECT IDENTIFIER
}

chassisInsFanSlotIndex                   OBJECT-TYPE
	SYNTAX     Integer32
	MAX-ACCESS read-only
	STATUS     current
	DESCRIPTION
		"This shows the index of fan module slot of server chassis."
	::= { chassisInsFanSlotEntry 1 }

chassisInsFanSlotNum                     OBJECT-TYPE
	SYNTAX     Integer32
	MAX-ACCESS read-only
	STATUS     current
	DESCRIPTION
		"This shows the number of fan module slots of server chassis."
	::= { chassisInsFanSlotEntry 2 }

chassisInsFanSlotExist                   OBJECT-TYPE
	SYNTAX     INTEGER {
		non-exist(1), exist(2), unknown(3)
	}
	MAX-ACCESS read-only
	STATUS     current
	DESCRIPTION
		"This shows the registrated state of fan module slot of server chassis."
	::= { chassisInsFanSlotEntry 3 }

chassisInsFanSlotObjectID                OBJECT-TYPE
	SYNTAX     OBJECT IDENTIFIER
	MAX-ACCESS read-only
	STATUS     current
	DESCRIPTION
		"This shows the object ID of fan module slot of server chassis."
	::= { chassisInsFanSlotEntry 4 }

chassisInsPowerSupplySlotTable           OBJECT-TYPE
	SYNTAX SEQUENCE OF chassisInsPowerSupplySlotEntry
	MAX-ACCESS not-accessible
	STATUS     current
	DESCRIPTION
		"This shows the table of power supply module slot of server chassis."
	::= { chassisInstall 11 }

chassisInsPowerSupplySlotEntry           OBJECT-TYPE
	SYNTAX     ChassisInsPowerSupplySlotEntry
	MAX-ACCESS not-accessible
	STATUS     current
	DESCRIPTION
		"This shows the entry of power supply module slot of server chassis."
	INDEX { chassisInsPowerSupplySlotIndex }
	::= { chassisInsPowerSupplySlotTable 1 }

ChassisInsPowerSupplySlotEntry ::= SEQUENCE {
	chassisInsPowerSupplySlotIndex
		Integer32,
	chassisInsPowerSupplySlotNum
		Integer32,
	chassisInsPowerSupplySlotExist
		INTEGER,
	chassisInsPowerSupplySlotObjectID
		OBJECT IDENTIFIER
}

chassisInsPowerSupplySlotIndex           OBJECT-TYPE
	SYNTAX     Integer32
	MAX-ACCESS read-only
	STATUS     current
	DESCRIPTION
		"This shows the index of power supply module slot of server chassis."
	::= { chassisInsPowerSupplySlotEntry 1 }

chassisInsPowerSupplySlotNum             OBJECT-TYPE
	SYNTAX     Integer32
	MAX-ACCESS read-only
	STATUS     current
	DESCRIPTION
		"This shows the number of power supply module slots of server chassis."
	::= { chassisInsPowerSupplySlotEntry 2 }

chassisInsPowerSupplySlotExist           OBJECT-TYPE
	SYNTAX     INTEGER {
		non-exist(1), exist(2), unknown(3)
	}
	MAX-ACCESS read-only
	STATUS     current
	DESCRIPTION
		"This shows the registrated state of power supply module slot of server chassis."
	::= { chassisInsPowerSupplySlotEntry 3 }

chassisInsPowerSupplySlotObjectID        OBJECT-TYPE
	SYNTAX     OBJECT IDENTIFIER
	MAX-ACCESS read-only
	STATUS     current
	DESCRIPTION
		"This shows the object ID of power supply module slot of server chassis."
	::= { chassisInsPowerSupplySlotEntry 4 }

chassisVoltageSensorTable                OBJECT-TYPE
	SYNTAX SEQUENCE OF chassisVoltageSensorEntry
	MAX-ACCESS not-accessible
	STATUS     current
	DESCRIPTION
		"This shows the table of voltage sensor of server chassis."
	::= { chassisState 50 }

chassisVoltageSensorEntry                OBJECT-TYPE
	SYNTAX     ChassisVoltageSensorEntry
	MAX-ACCESS not-accessible
	STATUS     current
	DESCRIPTION
		"This shows the entry of voltage sensor of server chassis."
	INDEX { chassisVoltageSensorIndex }
	::= { chassisVoltageSensorTable 1 }

ChassisVoltageSensorEntry ::= SEQUENCE {
	chassisVoltageSensorIndex
		Integer32,
	chassisVoltageSensorName
		DisplayString,
	chassisVoltageSensorValue
		Integer32,
	chassisVoltageSensorValid
		INTEGER
}

chassisVoltageSensorIndex                OBJECT-TYPE
	SYNTAX     Integer32
	MAX-ACCESS read-only
	STATUS     current
	DESCRIPTION
		"This shows the index of voltage sensor of server chassis."
	::= { chassisVoltageSensorEntry 1 }

chassisVoltageSensorName                 OBJECT-TYPE
	SYNTAX     DisplayString
	MAX-ACCESS read-only
	STATUS     current
	DESCRIPTION
		"This shows the voltage sensor name of server chassis."
	::= { chassisVoltageSensorEntry 2 }

chassisVoltageSensorValue                OBJECT-TYPE
	SYNTAX     Integer32
	UNITS      "0.1 V"
	MAX-ACCESS read-only
	STATUS     current
	DESCRIPTION
		"This shows the voltage sensor value of server chassis."
	::= { chassisVoltageSensorEntry 3 }

chassisVoltageSensorValid                OBJECT-TYPE
	SYNTAX     INTEGER {
		invalid(1), valid(2), unknown(3)
	}
	MAX-ACCESS read-only
	STATUS     current
	DESCRIPTION
		"This shows the validity of voltage sensor value of server chassis."
	::= { chassisVoltageSensorEntry 4 }

chassisTempSensorTable                   OBJECT-TYPE
	SYNTAX SEQUENCE OF chassisTempSensorEntry
	MAX-ACCESS not-accessible
	STATUS     current
	DESCRIPTION
		"This shows the table of temperature sensor of server chassis."
	::= { chassisState 51 }

chassisTempSensorEntry                   OBJECT-TYPE
	SYNTAX     ChassisTempSensorEntry
	MAX-ACCESS not-accessible
	STATUS     current
	DESCRIPTION
		"This shows the entry of temperature sensor of server chassis."
	INDEX { chassisTempSensorIndex }
	::= { chassisTempSensorTable 1 }

ChassisTempSensorEntry ::= SEQUENCE {
	chassisTempSensorIndex
		Integer32,
	chassisTempSensorName
		DisplayString,
	chassisTempSensorValue
		Integer32,
	chassisTempSensorValid
		INTEGER
}

chassisTempSensorIndex                   OBJECT-TYPE
	SYNTAX     Integer32
	MAX-ACCESS read-only
	STATUS     current
	DESCRIPTION
		"This shows the index of temperature sensor of server chassis."
	::= { chassisTempSensorEntry 1 }

chassisTempSensorName                    OBJECT-TYPE
	SYNTAX     DisplayString
	MAX-ACCESS read-only
	STATUS     current
	DESCRIPTION
		"This shows the temperature sensor name of server chassis."
	::= { chassisTempSensorEntry 2 }

chassisTempSensorValue                   OBJECT-TYPE
	SYNTAX     Integer32
	UNITS      "0.1 degrees C"
	MAX-ACCESS read-only
	STATUS     current
	DESCRIPTION
		"This shows the temperature sensor value of server chassis."
	::= { chassisTempSensorEntry 3 }

chassisTempSensorValid                   OBJECT-TYPE
	SYNTAX     INTEGER {
		invalid(1), valid(2), unknown(3)
	}
	MAX-ACCESS read-only
	STATUS     current
	DESCRIPTION
		"This shows the validity of temperature sensor value of server chassis."
	::= { chassisTempSensorEntry 4 }

chassisFWInfo                            OBJECT IDENTIFIER ::= { chassis 5 }

chassisFWInfoTotalVer                    OBJECT-TYPE
	SYNTAX     DisplayString
	MAX-ACCESS read-only
	STATUS     current
	DESCRIPTION
		"This shows the total current version of firmware of server chassis."
	::= { chassisFWInfo 1 }

chassisFWInfoTable                       OBJECT-TYPE
	SYNTAX SEQUENCE OF chassisFWInfoFWInfoEntry
	MAX-ACCESS not-accessible
	STATUS     current
	DESCRIPTION
		"This shows the table of firmware information of server chassis."
	::= { chassisFWInfo 2 }

chassisFWInfoFWInfoEntry                 OBJECT-TYPE
	SYNTAX     ChassisFWInfoFWInfoEntry
	MAX-ACCESS not-accessible
	STATUS     current
	DESCRIPTION
		"This shows the entry of firmware information of server chassis."
	INDEX { chassisFWInfoIndex }
	::= { chassisFWInfoTable 1 }

ChassisFWInfoFWInfoEntry ::= SEQUENCE {
	chassisFWInfoIndex
		Integer32,
	chassisFWInfoName
		DisplayString,
	chassisFWInfoCurrentVer
		DisplayString,
	chassisFWInfoNextVer
		DisplayString
}

chassisFWInfoIndex                       OBJECT-TYPE
	SYNTAX     Integer32
	MAX-ACCESS read-only
	STATUS     current
	DESCRIPTION
		"This shows the index of firmware information of server chassis."
	::= { chassisFWInfoFWInfoEntry 1 }

chassisFWInfoName                        OBJECT-TYPE
	SYNTAX     DisplayString
	MAX-ACCESS read-only
	STATUS     current
	DESCRIPTION
		"This shows the firmware name of server chassis."
	::= { chassisFWInfoFWInfoEntry 2 }

chassisFWInfoCurrentVer                  OBJECT-TYPE
	SYNTAX     DisplayString
	MAX-ACCESS read-only
	STATUS     current
	DESCRIPTION
		"This shows the firmware current version of server chassis."
	::= { chassisFWInfoFWInfoEntry 3 }

chassisFWInfoNextVer                     OBJECT-TYPE
	SYNTAX     DisplayString
	MAX-ACCESS read-only
	STATUS     current
	DESCRIPTION
		"This shows the firmware next version of server chassis."
	::= { chassisFWInfoFWInfoEntry 4 }

component                                OBJECT IDENTIFIER ::= { computeRack 2 }

fanModule                                OBJECT IDENTIFIER ::= { component 1 }

fanModule1                               OBJECT IDENTIFIER ::= { fanModule 1 }

fanModule1BasicInfo                      OBJECT IDENTIFIER ::= { fanModule1 1 }

fanModule1InfoType                       OBJECT-TYPE
	SYNTAX     DisplayString
	MAX-ACCESS read-only
	STATUS     current
	DESCRIPTION
		"This shows the type of fan module1."
	::= { fanModule1BasicInfo 1 }

fanModule1InfoProductName                OBJECT-TYPE
	SYNTAX     DisplayString
	MAX-ACCESS read-only
	STATUS     current
	DESCRIPTION
		"Reserved."
	::= { fanModule1BasicInfo 2 }

fanModule1InfoModel                      OBJECT-TYPE
	SYNTAX     DisplayString
	MAX-ACCESS read-only
	STATUS     current
	DESCRIPTION
		"Reserved."
	::= { fanModule1BasicInfo 3 }

fanModule1InfoSerialNum                  OBJECT-TYPE
	SYNTAX     DisplayString
	MAX-ACCESS read-only
	STATUS     current
	DESCRIPTION
		"Reserved."
	::= { fanModule1BasicInfo 4 }

fanModule1InfoProductVersion             OBJECT-TYPE
	SYNTAX     DisplayString
	MAX-ACCESS read-only
	STATUS     current
	DESCRIPTION
		"Reserved."
	::= { fanModule1BasicInfo 5 }

fanModule1InfoProductManufacturer        OBJECT-TYPE
	SYNTAX     DisplayString
	MAX-ACCESS read-only
	STATUS     current
	DESCRIPTION
		"Reserved."
	::= { fanModule1BasicInfo 6 }

fanModule1InfoBoardProductName           OBJECT-TYPE
	SYNTAX     DisplayString
	MAX-ACCESS read-only
	STATUS     current
	DESCRIPTION
		"Reserved."
	::= { fanModule1BasicInfo 7 }

fanModule1InfoBoardSerialNum             OBJECT-TYPE
	SYNTAX     DisplayString
	MAX-ACCESS read-only
	STATUS     current
	DESCRIPTION
		"Reserved."
	::= { fanModule1BasicInfo 8 }

fanModule1InfoBoardManufacturer          OBJECT-TYPE
	SYNTAX     DisplayString
	MAX-ACCESS read-only
	STATUS     current
	DESCRIPTION
		"Reserved."
	::= { fanModule1BasicInfo 9 }

fanModule1InfoSpec                       OBJECT IDENTIFIER ::= { fanModule1BasicInfo 20 }

fanModule1SpecMaxRPM                     OBJECT-TYPE
	SYNTAX     Integer32
	UNITS      "rpm"
	MAX-ACCESS read-only
	STATUS     current
	DESCRIPTION
		"This shows the maximum rpm of fan module1."
	::= { fanModule1InfoSpec 1 }

fanModule1SpecMaxAirVolume               OBJECT-TYPE
	SYNTAX     Integer32
	UNITS      "0.1 m^3/min"
	MAX-ACCESS read-only
	STATUS     current
	DESCRIPTION
		"This shows the maximum air volume of fan module1."
	::= { fanModule1InfoSpec 2 }

fanModule1SpecMinRPM                     OBJECT-TYPE
	SYNTAX     Integer32
	UNITS      "rpm"
	MAX-ACCESS read-only
	STATUS     current
	DESCRIPTION
		"This shows the minimum rpm of fan module1."
	::= { fanModule1InfoSpec 3 }

fanModule1SpecMinAirVolume               OBJECT-TYPE
	SYNTAX     Integer32
	UNITS      "0.1 m^3/min"
	MAX-ACCESS read-only
	STATUS     current
	DESCRIPTION
		"This shows the minimum air volume of fan module1."
	::= { fanModule1InfoSpec 4 }

fanModule1Capacity                       OBJECT IDENTIFIER ::= { fanModule1 2 }

fanModule1CapacityFan                    OBJECT-TYPE
	SYNTAX     Integer32
	MAX-ACCESS read-only
	STATUS     current
	DESCRIPTION
		"This shows the capacity of fans of fan module1."
	::= { fanModule1Capacity 1 }

fanModule1Settings                       OBJECT-TYPE
	SYNTAX     DisplayString
	MAX-ACCESS read-only
	STATUS     current
	DESCRIPTION
		"Reserved."
	::= { fanModule1 3 }

fanModule1State                          OBJECT IDENTIFIER ::= { fanModule1 4 }

fanModule1StateSlotNum                   OBJECT-TYPE
	SYNTAX     Integer32
	MAX-ACCESS read-only
	STATUS     current
	DESCRIPTION
		"This shows the number of installed slots of fan module1."
	::= { fanModule1State 1 }

fanModule1StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module1."
	::= { fanModule1State 2 }

fanModule1StateHealth                    OBJECT-TYPE
	SYNTAX     INTEGER {
		normal(1), fail(2), unknown(3)
	}
	MAX-ACCESS read-only
	STATUS     current
	DESCRIPTION
		"This shows the health state of fan module1."
	::= { fanModule1State 3 }

fanModule1StateRedundancy                OBJECT-TYPE
	SYNTAX     INTEGER {
		redundancy(1), non-redundancy(2), unknown(3)
	}
	MAX-ACCESS read-only
	STATUS     current
	DESCRIPTION
		"This shows the redundancy of fan module1."
	::= { fanModule1State 4 }

fanModule1StateAirVolume                 OBJECT-TYPE
	SYNTAX     Integer32
	UNITS      "0.1 m^3/min"
	MAX-ACCESS read-only
	STATUS     current
	DESCRIPTION
		"This shows the current air volume of fan module1."
	::= { fanModule1State 5 }

fanModule1StateLEDTable                  OBJECT-TYPE
	SYNTAX SEQUENCE OF fanModule1StateLEDEntry
	MAX-ACCESS not-accessible
	STATUS     current
	DESCRIPTION
		"This shows the table of LED of fan module1."
	::= { fanModule1State 6 }

fanModule1StateLEDEntry                  OBJECT-TYPE
	SYNTAX     FanModule1StateLEDEntry
	MAX-ACCESS not-accessible
	STATUS     current
	DESCRIPTION
		"This shows the entry of LED of fan module1."
	INDEX { fanModule1StateLEDIndex }
	::= { fanModule1StateLEDTable 1 }

FanModule1StateLEDEntry ::= SEQUENCE {
	fanModule1StateLEDIndex
		Integer32,
	fanModule1StateLEDName
		DisplayString,
	fanModule1StateLEDType
		DisplayString,
	fanModule1StateLEDState
		INTEGER,
	fanModule1StateLEDColor
		INTEGER
}

fanModule1StateLEDIndex                  OBJECT-TYPE
	SYNTAX     Integer32
	MAX-ACCESS read-only
	STATUS     current
	DESCRIPTION
		"This shows the index of LED of fan module1."
	::= { fanModule1StateLEDEntry 1 }

fanModule1StateLEDName                   OBJECT-TYPE
	SYNTAX     DisplayString
	MAX-ACCESS read-only
	STATUS     current
	DESCRIPTION
		"This shows the name of LED of fan module1."
	::= { fanModule1StateLEDEntry 2 }

fanModule1StateLEDType                   OBJECT-TYPE
	SYNTAX     DisplayString
	MAX-ACCESS read-only
	STATUS     current
	DESCRIPTION
		"Reserved."
	::= { fanModule1StateLEDEntry 3 }

fanModule1StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module1."
	::= { fanModule1StateLEDEntry 4 }

fanModule1StateLEDColor                  OBJECT-TYPE
	SYNTAX     INTEGER {
		blue(1), green(2), red(3), amber(4), unknown(5)
	}
	MAX-ACCESS read-only
	STATUS     current
	DESCRIPTION
		"This shows the color of LED of fan module1."
	::= { fanModule1StateLEDEntry 5 }

fanModule1StateFanTable                  OBJECT-TYPE
	SYNTAX SEQUENCE OF fanModule1StateFanEntry
	MAX-ACCESS not-accessible
	STATUS     current
	DESCRIPTION
		"This shows the table of fan of fan module1."
	::= { fanModule1State 10 }

fanModule1StateFanEntry                  OBJECT-TYPE
	SYNTAX     FanModule1StateFanEntry
	MAX-ACCESS not-accessible
	STATUS     current
	DESCRIPTION
		"This shows the entry of fan of fan module1."
	INDEX { fanModule1StateFanIndex }
	::= { fanModule1StateFanTable 1 }

FanModule1StateFanEntry ::= SEQUENCE {
	fanModule1StateFanIndex
		Integer32,
	fanModule1StateFanLocation
		DisplayString,
	fanModule1StateFanRPM
		Integer32,
	fanModule1StateFanRPMValid
		INTEGER
}

fanModule1StateFanIndex                  OBJECT-TYPE
	SYNTAX     Integer32
	MAX-ACCESS read-only
	STATUS     current
	DESCRIPTION
		"This shows the index of fan of fan module1."
	::= { fanModule1StateFanEntry 1 }

fanModule1StateFanLocation               OBJECT-TYPE
	SYNTAX     DisplayString
	MAX-ACCESS read-only
	STATUS     current
	DESCRIPTION
		"This shows the location of fan of fan module1."
	::= { fanModule1StateFanEntry 2 }

fanModule1StateFanRPM                    OBJECT-TYPE
	SYNTAX     Integer32
	UNITS      "rpm"
	MAX-ACCESS read-only
	STATUS     current
	DESCRIPTION
		"This shows the rpm value of fan module1."
	::= { fanModule1StateFanEntry 3 }

fanModule1StateFanRPMValid               OBJECT-TYPE
	SYNTAX     INTEGER {
		invalid(1), valid(2), unknown(3)
	}
	MAX-ACCESS read-only
	STATUS     current
	DESCRIPTION
		"This shows the validity of fan rpm value of fan module1."
	::= { fanModule1StateFanEntry 4 }

fanModule2                               OBJECT IDENTIFIER ::= { fanModule 2 }

fanModule2BasicInfo                      OBJECT IDENTIFIER ::= { fanModule2 1 }

fanModule2InfoType                       OBJECT-TYPE
	SYNTAX     DisplayString
	MAX-ACCESS read-only
	STATUS     current
	DESCRIPTION
		"This shows the type of fan module2."
	::= { fanModule2BasicInfo 1 }

fanModule2InfoProductName                OBJECT-TYPE
	SYNTAX     DisplayString
	MAX-ACCESS read-only
	STATUS     current
	DESCRIPTION
		"Reserved."
	::= { fanModule2BasicInfo 2 }

fanModule2InfoModel                      OBJECT-TYPE
	SYNTAX     DisplayString
	MAX-ACCESS read-only
	STATUS     current
	DESCRIPTION
		"Reserved."
	::= { fanModule2BasicInfo 3 }

fanModule2InfoSerialNum                  OBJECT-TYPE
	SYNTAX     DisplayString
	MAX-ACCESS read-only
	STATUS     current
	DESCRIPTION
		"Reserved."
	::= { fanModule2BasicInfo 4 }

fanModule2InfoProductVersion             OBJECT-TYPE
	SYNTAX     DisplayString
	MAX-ACCESS read-only
	STATUS     current
	DESCRIPTION
		"Reserved."
	::= { fanModule2BasicInfo 5 }

fanModule2InfoProductManufacturer        OBJECT-TYPE
	SYNTAX     DisplayString
	MAX-ACCESS read-only
	STATUS     current
	DESCRIPTION
		"Reserved."
	::= { fanModule2BasicInfo 6 }

fanModule2InfoBoardProductName           OBJECT-TYPE
	SYNTAX     DisplayString
	MAX-ACCESS read-only
	STATUS     current
	DESCRIPTION
		"Reserved."
	::= { fanModule2BasicInfo 7 }

fanModule2InfoBoardSerialNum             OBJECT-TYPE
	SYNTAX     DisplayString
	MAX-ACCESS read-only
	STATUS     current
	DESCRIPTION
		"Reserved."
	::= { fanModule2BasicInfo 8 }

fanModule2InfoBoardManufacturer          OBJECT-TYPE
	SYNTAX     DisplayString
	MAX-ACCESS read-only
	STATUS     current
	DESCRIPTION
		"Reserved."
	::= { fanModule2BasicInfo 9 }

fanModule2InfoSpec                       OBJECT IDENTIFIER ::= { fanModule2BasicInfo 20 }

fanModule2SpecMaxRPM                     OBJECT-TYPE
	SYNTAX     Integer32
	UNITS      "rpm"
	MAX-ACCESS read-only
	STATUS     current
	DESCRIPTION
		"This shows the maximum rpm of fan module2."
	::= { fanModule2InfoSpec 1 }

fanModule2SpecMaxAirVolume               OBJECT-TYPE
	SYNTAX     Integer32
	UNITS      "0.1 m^3/min"
	MAX-ACCESS read-only
	STATUS     current
	DESCRIPTION
		"This shows the maximum air volume of fan module2."
	::= { fanModule2InfoSpec 2 }

fanModule2SpecMinRPM                     OBJECT-TYPE
	SYNTAX     Integer32
	UNITS      "rpm"
	MAX-ACCESS read-only
	STATUS     current
	DESCRIPTION
		"This shows the minimum rpm of fan module2."
	::= { fanModule2InfoSpec 3 }

fanModule2SpecMinAirVolume               OBJECT-TYPE
	SYNTAX     Integer32
	UNITS      "0.1 m^3/min"
	MAX-ACCESS read-only
	STATUS     current
	DESCRIPTION
		"This shows the minimum air volume of fan module2."
	::= { fanModule2InfoSpec 4 }

fanModule2Capacity                       OBJECT IDENTIFIER ::= { fanModule2 2 }

fanModule2CapacityFan                    OBJECT-TYPE
	SYNTAX     Integer32
	MAX-ACCESS read-only
	STATUS     current
	DESCRIPTION
		"This shows the capacity of fans of fan module2."
	::= { fanModule2Capacity 1 }

fanModule2Settings                       OBJECT-TYPE
	SYNTAX     DisplayString
	MAX-ACCESS read-only
	STATUS     current
	DESCRIPTION
		"Reserved."
	::= { fanModule2 3 }

fanModule2State                          OBJECT IDENTIFIER ::= { fanModule2 4 }

fanModule2StateSlotNum                   OBJECT-TYPE
	SYNTAX     Integer32
	MAX-ACCESS read-only
	STATUS     current
	DESCRIPTION
		"This shows the number of installed slots of fan module2."
	::= { fanModule2State 1 }

fanModule2StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module2."
	::= { fanModule2State 2 }

fanModule2StateHealth                    OBJECT-TYPE
	SYNTAX     INTEGER {
		normal(1), fail(2), unknown(3)
	}
	MAX-ACCESS read-only
	STATUS     current
	DESCRIPTION
		"This shows the health state of fan module2."
	::= { fanModule2State 3 }

fanModule2StateRedundancy                OBJECT-TYPE
	SYNTAX     INTEGER {
		redundancy(1), non-redundancy(2), unknown(3)
	}
	MAX-ACCESS read-only
	STATUS     current
	DESCRIPTION
		"This shows the redundancy of fan module2."
	::= { fanModule2State 4 }

fanModule2StateAirVolume                 OBJECT-TYPE
	SYNTAX     Integer32
	UNITS      "0.1 m^3/min"
	MAX-ACCESS read-only
	STATUS     current
	DESCRIPTION
		"This shows the current air volume of fan module2."
	::= { fanModule2State 5 }

fanModule2StateLEDTable                  OBJECT-TYPE
	SYNTAX SEQUENCE OF fanModule2StateLEDEntry
	MAX-ACCESS not-accessible
	STATUS     current
	DESCRIPTION
		"This shows the table of LED of fan module2."
	::= { fanModule2State 6 }

fanModule2StateLEDEntry                  OBJECT-TYPE
	SYNTAX     FanModule2StateLEDEntry
	MAX-ACCESS not-accessible
	STATUS     current
	DESCRIPTION
		"This shows the entry of LED of fan module2."
	INDEX { fanModule2StateLEDIndex }
	::= { fanModule2StateLEDTable 1 }

FanModule2StateLEDEntry ::= SEQUENCE {
	fanModule2StateLEDIndex
		Integer32,
	fanModule2StateLEDName
		DisplayString,
	fanModule2StateLEDType
		DisplayString,
	fanModule2StateLEDState
		INTEGER,
	fanModule2StateLEDColor
		INTEGER
}

fanModule2StateLEDIndex                  OBJECT-TYPE
	SYNTAX     Integer32
	MAX-ACCESS read-only
	STATUS     current
	DESCRIPTION
		"This shows the index of LED of fan module2."
	::= { fanModule2StateLEDEntry 1 }

fanModule2StateLEDName                   OBJECT-TYPE
	SYNTAX     DisplayString
	MAX-ACCESS read-only
	STATUS     current
	DESCRIPTION
		"This shows the name of LED of fan module2."
	::= { fanModule2StateLEDEntry 2 }

fanModule2StateLEDType                   OBJECT-TYPE
	SYNTAX     DisplayString
	MAX-ACCESS read-only
	STATUS     current
	DESCRIPTION
		"Reserved."
	::= { fanModule2StateLEDEntry 3 }

fanModule2StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module2."
	::= { fanModule2StateLEDEntry 4 }

fanModule2StateLEDColor                  OBJECT-TYPE
	SYNTAX     INTEGER {
		blue(1), green(2), red(3), amber(4), unknown(5)
	}
	MAX-ACCESS read-only
	STATUS     current
	DESCRIPTION
		"This shows the color of LED of fan module2."
	::= { fanModule2StateLEDEntry 5 }

fanModule2StateFanTable                  OBJECT-TYPE
	SYNTAX SEQUENCE OF fanModule2StateFanEntry
	MAX-ACCESS not-accessible
	STATUS     current
	DESCRIPTION
		"This shows the table of fan of fan module2."
	::= { fanModule2State 10 }

fanModule2StateFanEntry                  OBJECT-TYPE
	SYNTAX     FanModule2StateFanEntry
	MAX-ACCESS not-accessible
	STATUS     current
	DESCRIPTION
		"This shows the entry of fan of fan module2."
	INDEX { fanModule2StateFanIndex }
	::= { fanModule2StateFanTable 1 }

FanModule2StateFanEntry ::= SEQUENCE {
	fanModule2StateFanIndex
		Integer32,
	fanModule2StateFanLocation
		DisplayString,
	fanModule2StateFanRPM
		Integer32,
	fanModule2StateFanRPMValid
		INTEGER
}

fanModule2StateFanIndex                  OBJECT-TYPE
	SYNTAX     Integer32
	MAX-ACCESS read-only
	STATUS     current
	DESCRIPTION
		"This shows the index of fan of fan module2."
	::= { fanModule2StateFanEntry 1 }

fanModule2StateFanLocation               OBJECT-TYPE
	SYNTAX     DisplayString
	MAX-ACCESS read-only
	STATUS     current
	DESCRIPTION
		"This shows the location of fan of fan module2."
	::= { fanModule2StateFanEntry 2 }

fanModule2StateFanRPM                    OBJECT-TYPE
	SYNTAX     Integer32
	UNITS      "rpm"
	MAX-ACCESS read-only
	STATUS     current
	DESCRIPTION
		"This shows the rpm value of fan module2."
	::= { fanModule2StateFanEntry 3 }

fanModule2StateFanRPMValid               OBJECT-TYPE
	SYNTAX     INTEGER {
		invalid(1), valid(2), unknown(3)
	}
	MAX-ACCESS read-only
	STATUS     current
	DESCRIPTION
		"This shows the validity of fan rpm value of fan module2."
	::= { fanModule2StateFanEntry 4 }

fanModule3                               OBJECT IDENTIFIER ::= { fanModule 3 }

fanModule3BasicInfo                      OBJECT IDENTIFIER ::= { fanModule3 1 }

fanModule3InfoType                       OBJECT-TYPE
	SYNTAX     DisplayString
	MAX-ACCESS read-only
	STATUS     current
	DESCRIPTION
		"This shows the type of fan module3."
	::= { fanModule3BasicInfo 1 }

fanModule3InfoProductName                OBJECT-TYPE
	SYNTAX     DisplayString
	MAX-ACCESS read-only
	STATUS     current
	DESCRIPTION
		"Reserved."
	::= { fanModule3BasicInfo 2 }

fanModule3InfoModel                      OBJECT-TYPE
	SYNTAX     DisplayString
	MAX-ACCESS read-only
	STATUS     current
	DESCRIPTION
		"Reserved."
	::= { fanModule3BasicInfo 3 }

fanModule3InfoSerialNum                  OBJECT-TYPE
	SYNTAX     DisplayString
	MAX-ACCESS read-only
	STATUS     current
	DESCRIPTION
		"Reserved."
	::= { fanModule3BasicInfo 4 }

fanModule3InfoProductVersion             OBJECT-TYPE
	SYNTAX     DisplayString
	MAX-ACCESS read-only
	STATUS     current
	DESCRIPTION
		"Reserved."
	::= { fanModule3BasicInfo 5 }

fanModule3InfoProductManufacturer        OBJECT-TYPE
	SYNTAX     DisplayString
	MAX-ACCESS read-only
	STATUS     current
	DESCRIPTION
		"Reserved."
	::= { fanModule3BasicInfo 6 }

fanModule3InfoBoardProductName           OBJECT-TYPE
	SYNTAX     DisplayString
	MAX-ACCESS read-only
	STATUS     current
	DESCRIPTION
		"Reserved."
	::= { fanModule3BasicInfo 7 }

fanModule3InfoBoardSerialNum             OBJECT-TYPE
	SYNTAX     DisplayString
	MAX-ACCESS read-only
	STATUS     current
	DESCRIPTION
		"Reserved."
	::= { fanModule3BasicInfo 8 }

fanModule3InfoBoardManufacturer          OBJECT-TYPE
	SYNTAX     DisplayString
	MAX-ACCESS read-only
	STATUS     current
	DESCRIPTION
		"Reserved."
	::= { fanModule3BasicInfo 9 }

fanModule3InfoSpec                       OBJECT IDENTIFIER ::= { fanModule3BasicInfo 20 }

fanModule3SpecMaxRPM                     OBJECT-TYPE
	SYNTAX     Integer32
	UNITS      "rpm"
	MAX-ACCESS read-only
	STATUS     current
	DESCRIPTION
		"This shows the maximum rpm of fan module3."
	::= { fanModule3InfoSpec 1 }

fanModule3SpecMaxAirVolume               OBJECT-TYPE
	SYNTAX     Integer32
	UNITS      "0.1 m^3/min"
	MAX-ACCESS read-only
	STATUS     current
	DESCRIPTION
		"This shows the maximum air volume of fan module3."
	::= { fanModule3InfoSpec 2 }

fanModule3SpecMinRPM                     OBJECT-TYPE
	SYNTAX     Integer32
	UNITS      "rpm"
	MAX-ACCESS read-only
	STATUS     current
	DESCRIPTION
		"This shows the minimum rpm of fan module3."
	::= { fanModule3InfoSpec 3 }

fanModule3SpecMinAirVolume               OBJECT-TYPE
	SYNTAX     Integer32
	UNITS      "0.1 m^3/min"
	MAX-ACCESS read-only
	STATUS     current
	DESCRIPTION
		"This shows the minimum air volume of fan module3."
	::= { fanModule3InfoSpec 4 }

fanModule3Capacity                       OBJECT IDENTIFIER ::= { fanModule3 2 }

fanModule3CapacityFan                    OBJECT-TYPE
	SYNTAX     Integer32
	MAX-ACCESS read-only
	STATUS     current
	DESCRIPTION
		"This shows the capacity of fans of fan module3."
	::= { fanModule3Capacity 1 }

fanModule3Settings                       OBJECT-TYPE
	SYNTAX     DisplayString
	MAX-ACCESS read-only
	STATUS     current
	DESCRIPTION
		"Reserved."
	::= { fanModule3 3 }

fanModule3State                          OBJECT IDENTIFIER ::= { fanModule3 4 }

fanModule3StateSlotNum                   OBJECT-TYPE
	SYNTAX     Integer32
	MAX-ACCESS read-only
	STATUS     current
	DESCRIPTION
		"This shows the number of installed slots of fan module3."
	::= { fanModule3State 1 }

fanModule3StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module3."
	::= { fanModule3State 2 }

fanModule3StateHealth                    OBJECT-TYPE
	SYNTAX     INTEGER {
		normal(1), fail(2), unknown(3)
	}
	MAX-ACCESS read-only
	STATUS     current
	DESCRIPTION
		"This shows the health state of fan module3."
	::= { fanModule3State 3 }

fanModule3StateRedundancy                OBJECT-TYPE
	SYNTAX     INTEGER {
		redundancy(1), non-redundancy(2), unknown(3)
	}
	MAX-ACCESS read-only
	STATUS     current
	DESCRIPTION
		"This shows the redundancy of fan module3."
	::= { fanModule3State 4 }

fanModule3StateAirVolume                 OBJECT-TYPE
	SYNTAX     Integer32
	UNITS      "0.1 m^3/min"
	MAX-ACCESS read-only
	STATUS     current
	DESCRIPTION
		"This shows the current air volume of fan module3."
	::= { fanModule3State 5 }

fanModule3StateLEDTable                  OBJECT-TYPE
	SYNTAX SEQUENCE OF fanModule3StateLEDEntry
	MAX-ACCESS not-accessible
	STATUS     current
	DESCRIPTION
		"This shows the table of LED of fan module3."
	::= { fanModule3State 6 }

fanModule3StateLEDEntry                  OBJECT-TYPE
	SYNTAX     FanModule3StateLEDEntry
	MAX-ACCESS not-accessible
	STATUS     current
	DESCRIPTION
		"This shows the entry of LED of fan module3."
	INDEX { fanModule3StateLEDIndex }
	::= { fanModule3StateLEDTable 1 }

FanModule3StateLEDEntry ::= SEQUENCE {
	fanModule3StateLEDIndex
		Integer32,
	fanModule3StateLEDName
		DisplayString,
	fanModule3StateLEDType
		DisplayString,
	fanModule3StateLEDState
		INTEGER,
	fanModule3StateLEDColor
		INTEGER
}

fanModule3StateLEDIndex                  OBJECT-TYPE
	SYNTAX     Integer32
	MAX-ACCESS read-only
	STATUS     current
	DESCRIPTION
		"This shows the index of LED of fan module3."
	::= { fanModule3StateLEDEntry 1 }

fanModule3StateLEDName                   OBJECT-TYPE
	SYNTAX     DisplayString
	MAX-ACCESS read-only
	STATUS     current
	DESCRIPTION
		"This shows the name of LED of fan module3."
	::= { fanModule3StateLEDEntry 2 }

fanModule3StateLEDType                   OBJECT-TYPE
	SYNTAX     DisplayString
	MAX-ACCESS read-only
	STATUS     current
	DESCRIPTION
		"Reserved."
	::= { fanModule3StateLEDEntry 3 }

fanModule3StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module3."
	::= { fanModule3StateLEDEntry 4 }

fanModule3StateLEDColor                  OBJECT-TYPE
	SYNTAX     INTEGER {
		blue(1), green(2), red(3), amber(4), unknown(5)
	}
	MAX-ACCESS read-only
	STATUS     current
	DESCRIPTION
		"This shows the color of LED of fan module3."
	::= { fanModule3StateLEDEntry 5 }

fanModule3StateFanTable                  OBJECT-TYPE
	SYNTAX SEQUENCE OF fanModule3StateFanEntry
	MAX-ACCESS not-accessible
	STATUS     current
	DESCRIPTION
		"This shows the table of fan of fan module3."
	::= { fanModule3State 10 }

fanModule3StateFanEntry                  OBJECT-TYPE
	SYNTAX     FanModule3StateFanEntry
	MAX-ACCESS not-accessible
	STATUS     current
	DESCRIPTION
		"This shows the entry of fan of fan module3."
	INDEX { fanModule3StateFanIndex }
	::= { fanModule3StateFanTable 1 }

FanModule3StateFanEntry ::= SEQUENCE {
	fanModule3StateFanIndex
		Integer32,
	fanModule3StateFanLocation
		DisplayString,
	fanModule3StateFanRPM
		Integer32,
	fanModule3StateFanRPMValid
		INTEGER
}

fanModule3StateFanIndex                  OBJECT-TYPE
	SYNTAX     Integer32
	MAX-ACCESS read-only
	STATUS     current
	DESCRIPTION
		"This shows the index of fan of fan module3."
	::= { fanModule3StateFanEntry 1 }

fanModule3StateFanLocation               OBJECT-TYPE
	SYNTAX     DisplayString
	MAX-ACCESS read-only
	STATUS     current
	DESCRIPTION
		"This shows the location of fan of fan module3."
	::= { fanModule3StateFanEntry 2 }

fanModule3StateFanRPM                    OBJECT-TYPE
	SYNTAX     Integer32
	UNITS      "rpm"
	MAX-ACCESS read-only
	STATUS     current
	DESCRIPTION
		"This shows the rpm value of fan module3."
	::= { fanModule3StateFanEntry 3 }

fanModule3StateFanRPMValid               OBJECT-TYPE
	SYNTAX     INTEGER {
		invalid(1), valid(2), unknown(3)
	}
	MAX-ACCESS read-only
	STATUS     current
	DESCRIPTION
		"This shows the validity of fan rpm value of fan module3."
	::= { fanModule3StateFanEntry 4 }

fanModule4                               OBJECT IDENTIFIER ::= { fanModule 4 }

fanModule4BasicInfo                      OBJECT IDENTIFIER ::= { fanModule4 1 }

fanModule4InfoType                       OBJECT-TYPE
	SYNTAX     DisplayString
	MAX-ACCESS read-only
	STATUS     current
	DESCRIPTION
		"This shows the type of fan module4."
	::= { fanModule4BasicInfo 1 }

fanModule4InfoProductName                OBJECT-TYPE
	SYNTAX     DisplayString
	MAX-ACCESS read-only
	STATUS     current
	DESCRIPTION
		"Reserved."
	::= { fanModule4BasicInfo 2 }

fanModule4InfoModel                      OBJECT-TYPE
	SYNTAX     DisplayString
	MAX-ACCESS read-only
	STATUS     current
	DESCRIPTION
		"Reserved."
	::= { fanModule4BasicInfo 3 }

fanModule4InfoSerialNum                  OBJECT-TYPE
	SYNTAX     DisplayString
	MAX-ACCESS read-only
	STATUS     current
	DESCRIPTION
		"Reserved."
	::= { fanModule4BasicInfo 4 }

fanModule4InfoProductVersion             OBJECT-TYPE
	SYNTAX     DisplayString
	MAX-ACCESS read-only
	STATUS     current
	DESCRIPTION
		"Reserved."
	::= { fanModule4BasicInfo 5 }

fanModule4InfoProductManufacturer        OBJECT-TYPE
	SYNTAX     DisplayString
	MAX-ACCESS read-only
	STATUS     current
	DESCRIPTION
		"Reserved."
	::= { fanModule4BasicInfo 6 }

fanModule4InfoBoardProductName           OBJECT-TYPE
	SYNTAX     DisplayString
	MAX-ACCESS read-only
	STATUS     current
	DESCRIPTION
		"Reserved."
	::= { fanModule4BasicInfo 7 }

fanModule4InfoBoardSerialNum             OBJECT-TYPE
	SYNTAX     DisplayString
	MAX-ACCESS read-only
	STATUS     current
	DESCRIPTION
		"Reserved."
	::= { fanModule4BasicInfo 8 }

fanModule4InfoBoardManufacturer          OBJECT-TYPE
	SYNTAX     DisplayString
	MAX-ACCESS read-only
	STATUS     current
	DESCRIPTION
		"Reserved."
	::= { fanModule4BasicInfo 9 }

fanModule4InfoSpec                       OBJECT IDENTIFIER ::= { fanModule4BasicInfo 20 }

fanModule4SpecMaxRPM                     OBJECT-TYPE
	SYNTAX     Integer32
	UNITS      "rpm"
	MAX-ACCESS read-only
	STATUS     current
	DESCRIPTION
		"This shows the maximum rpm of fan module4."
	::= { fanModule4InfoSpec 1 }

fanModule4SpecMaxAirVolume               OBJECT-TYPE
	SYNTAX     Integer32
	UNITS      "0.1 m^3/min"
	MAX-ACCESS read-only
	STATUS     current
	DESCRIPTION
		"This shows the maximum air volume of fan module4."
	::= { fanModule4InfoSpec 2 }

fanModule4SpecMinRPM                     OBJECT-TYPE
	SYNTAX     Integer32
	UNITS      "rpm"
	MAX-ACCESS read-only
	STATUS     current
	DESCRIPTION
		"This shows the minimum rpm of fan module4."
	::= { fanModule4InfoSpec 3 }

fanModule4SpecMinAirVolume               OBJECT-TYPE
	SYNTAX     Integer32
	UNITS      "0.1 m^3/min"
	MAX-ACCESS read-only
	STATUS     current
	DESCRIPTION
		"This shows the minimum air volume of fan module4."
	::= { fanModule4InfoSpec 4 }

fanModule4Capacity                       OBJECT IDENTIFIER ::= { fanModule4 2 }

fanModule4CapacityFan                    OBJECT-TYPE
	SYNTAX     Integer32
	MAX-ACCESS read-only
	STATUS     current
	DESCRIPTION
		"This shows the capacity of fans of fan module4."
	::= { fanModule4Capacity 1 }

fanModule4Settings                       OBJECT-TYPE
	SYNTAX     DisplayString
	MAX-ACCESS read-only
	STATUS     current
	DESCRIPTION
		"Reserved."
	::= { fanModule4 3 }

fanModule4State                          OBJECT IDENTIFIER ::= { fanModule4 4 }

fanModule4StateSlotNum                   OBJECT-TYPE
	SYNTAX     Integer32
	MAX-ACCESS read-only
	STATUS     current
	DESCRIPTION
		"This shows the number of installed slots of fan module4."
	::= { fanModule4State 1 }

fanModule4StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module4."
	::= { fanModule4State 2 }

fanModule4StateHealth                    OBJECT-TYPE
	SYNTAX     INTEGER {
		normal(1), fail(2), unknown(3)
	}
	MAX-ACCESS read-only
	STATUS     current
	DESCRIPTION
		"This shows the health state of fan module4."
	::= { fanModule4State 3 }

fanModule4StateRedundancy                OBJECT-TYPE
	SYNTAX     INTEGER {
		redundancy(1), non-redundancy(2), unknown(3)
	}
	MAX-ACCESS read-only
	STATUS     current
	DESCRIPTION
		"This shows the redundancy of fan module4."
	::= { fanModule4State 4 }

fanModule4StateAirVolume                 OBJECT-TYPE
	SYNTAX     Integer32
	UNITS      "0.1 m^3/min"
	MAX-ACCESS read-only
	STATUS     current
	DESCRIPTION
		"This shows the current air volume of fan module4."
	::= { fanModule4State 5 }

fanModule4StateLEDTable                  OBJECT-TYPE
	SYNTAX SEQUENCE OF fanModule4StateLEDEntry
	MAX-ACCESS not-accessible
	STATUS     current
	DESCRIPTION
		"This shows the table of LED of fan module4."
	::= { fanModule4State 6 }

fanModule4StateLEDEntry                  OBJECT-TYPE
	SYNTAX     FanModule4StateLEDEntry
	MAX-ACCESS not-accessible
	STATUS     current
	DESCRIPTION
		"This shows the entry of LED of fan module4."
	INDEX { fanModule4StateLEDIndex }
	::= { fanModule4StateLEDTable 1 }

FanModule4StateLEDEntry ::= SEQUENCE {
	fanModule4StateLEDIndex
		Integer32,
	fanModule4StateLEDName
		DisplayString,
	fanModule4StateLEDType
		DisplayString,
	fanModule4StateLEDState
		INTEGER,
	fanModule4StateLEDColor
		INTEGER
}

fanModule4StateLEDIndex                  OBJECT-TYPE
	SYNTAX     Integer32
	MAX-ACCESS read-only
	STATUS     current
	DESCRIPTION
		"This shows the index of LED of fan module4."
	::= { fanModule4StateLEDEntry 1 }

fanModule4StateLEDName                   OBJECT-TYPE
	SYNTAX     DisplayString
	MAX-ACCESS read-only
	STATUS     current
	DESCRIPTION
		"This shows the name of LED of fan module4."
	::= { fanModule4StateLEDEntry 2 }

fanModule4StateLEDType                   OBJECT-TYPE
	SYNTAX     DisplayString
	MAX-ACCESS read-only
	STATUS     current
	DESCRIPTION
		"Reserved."
	::= { fanModule4StateLEDEntry 3 }

fanModule4StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module4."
	::= { fanModule4StateLEDEntry 4 }

fanModule4StateLEDColor                  OBJECT-TYPE
	SYNTAX     INTEGER {
		blue(1), green(2), red(3), amber(4), unknown(5)
	}
	MAX-ACCESS read-only
	STATUS     current
	DESCRIPTION
		"This shows the color of LED of fan module4."
	::= { fanModule4StateLEDEntry 5 }

fanModule4StateFanTable                  OBJECT-TYPE
	SYNTAX SEQUENCE OF fanModule4StateFanEntry
	MAX-ACCESS not-accessible
	STATUS     current
	DESCRIPTION
		"This shows the table of fan of fan module4."
	::= { fanModule4State 10 }

fanModule4StateFanEntry                  OBJECT-TYPE
	SYNTAX     FanModule4StateFanEntry
	MAX-ACCESS not-accessible
	STATUS     current
	DESCRIPTION
		"This shows the entry of fan of fan module4."
	INDEX { fanModule4StateFanIndex }
	::= { fanModule4StateFanTable 1 }

FanModule4StateFanEntry ::= SEQUENCE {
	fanModule4StateFanIndex
		Integer32,
	fanModule4StateFanLocation
		DisplayString,
	fanModule4StateFanRPM
		Integer32,
	fanModule4StateFanRPMValid
		INTEGER
}

fanModule4StateFanIndex                  OBJECT-TYPE
	SYNTAX     Integer32
	MAX-ACCESS read-only
	STATUS     current
	DESCRIPTION
		"This shows the index of fan of fan module4."
	::= { fanModule4StateFanEntry 1 }

fanModule4StateFanLocation               OBJECT-TYPE
	SYNTAX     DisplayString
	MAX-ACCESS read-only
	STATUS     current
	DESCRIPTION
		"This shows the location of fan of fan module4."
	::= { fanModule4StateFanEntry 2 }

fanModule4StateFanRPM                    OBJECT-TYPE
	SYNTAX     Integer32
	UNITS      "rpm"
	MAX-ACCESS read-only
	STATUS     current
	DESCRIPTION
		"This shows the rpm value of fan module4."
	::= { fanModule4StateFanEntry 3 }

fanModule4StateFanRPMValid               OBJECT-TYPE
	SYNTAX     INTEGER {
		invalid(1), valid(2), unknown(3)
	}
	MAX-ACCESS read-only
	STATUS     current
	DESCRIPTION
		"This shows the validity of fan rpm value of fan module4."
	::= { fanModule4StateFanEntry 4 }

fanModule5                               OBJECT IDENTIFIER ::= { fanModule 5 }

fanModule5BasicInfo                      OBJECT IDENTIFIER ::= { fanModule5 1 }

fanModule5InfoType                       OBJECT-TYPE
	SYNTAX     DisplayString
	MAX-ACCESS read-only
	STATUS     current
	DESCRIPTION
		"This shows the type of fan module5."
	::= { fanModule5BasicInfo 1 }

fanModule5InfoProductName                OBJECT-TYPE
	SYNTAX     DisplayString
	MAX-ACCESS read-only
	STATUS     current
	DESCRIPTION
		"Reserved."
	::= { fanModule5BasicInfo 2 }

fanModule5InfoModel                      OBJECT-TYPE
	SYNTAX     DisplayString
	MAX-ACCESS read-only
	STATUS     current
	DESCRIPTION
		"Reserved."
	::= { fanModule5BasicInfo 3 }

fanModule5InfoSerialNum                  OBJECT-TYPE
	SYNTAX     DisplayString
	MAX-ACCESS read-only
	STATUS     current
	DESCRIPTION
		"Reserved."
	::= { fanModule5BasicInfo 4 }

fanModule5InfoProductVersion             OBJECT-TYPE
	SYNTAX     DisplayString
	MAX-ACCESS read-only
	STATUS     current
	DESCRIPTION
		"Reserved."
	::= { fanModule5BasicInfo 5 }

fanModule5InfoProductManufacturer        OBJECT-TYPE
	SYNTAX     DisplayString
	MAX-ACCESS read-only
	STATUS     current
	DESCRIPTION
		"Reserved."
	::= { fanModule5BasicInfo 6 }

fanModule5InfoBoardProductName           OBJECT-TYPE
	SYNTAX     DisplayString
	MAX-ACCESS read-only
	STATUS     current
	DESCRIPTION
		"Reserved."
	::= { fanModule5BasicInfo 7 }

fanModule5InfoBoardSerialNum             OBJECT-TYPE
	SYNTAX     DisplayString
	MAX-ACCESS read-only
	STATUS     current
	DESCRIPTION
		"Reserved."
	::= { fanModule5BasicInfo 8 }

fanModule5InfoBoardManufacturer          OBJECT-TYPE
	SYNTAX     DisplayString
	MAX-ACCESS read-only
	STATUS     current
	DESCRIPTION
		"Reserved."
	::= { fanModule5BasicInfo 9 }

fanModule5InfoSpec                       OBJECT IDENTIFIER ::= { fanModule5BasicInfo 20 }

fanModule5SpecMaxRPM                     OBJECT-TYPE
	SYNTAX     Integer32
	UNITS      "rpm"
	MAX-ACCESS read-only
	STATUS     current
	DESCRIPTION
		"This shows the maximum rpm of fan module5."
	::= { fanModule5InfoSpec 1 }

fanModule5SpecMaxAirVolume               OBJECT-TYPE
	SYNTAX     Integer32
	UNITS      "0.1 m^3/min"
	MAX-ACCESS read-only
	STATUS     current
	DESCRIPTION
		"This shows the maximum air volume of fan module5."
	::= { fanModule5InfoSpec 2 }

fanModule5SpecMinRPM                     OBJECT-TYPE
	SYNTAX     Integer32
	UNITS      "rpm"
	MAX-ACCESS read-only
	STATUS     current
	DESCRIPTION
		"This shows the minimum rpm of fan module5."
	::= { fanModule5InfoSpec 3 }

fanModule5SpecMinAirVolume               OBJECT-TYPE
	SYNTAX     Integer32
	UNITS      "0.1 m^3/min"
	MAX-ACCESS read-only
	STATUS     current
	DESCRIPTION
		"This shows the minimum air volume of fan module5."
	::= { fanModule5InfoSpec 4 }

fanModule5Capacity                       OBJECT IDENTIFIER ::= { fanModule5 2 }

fanModule5CapacityFan                    OBJECT-TYPE
	SYNTAX     Integer32
	MAX-ACCESS read-only
	STATUS     current
	DESCRIPTION
		"This shows the capacity of fans of fan module5."
	::= { fanModule5Capacity 1 }

fanModule5Settings                       OBJECT-TYPE
	SYNTAX     DisplayString
	MAX-ACCESS read-only
	STATUS     current
	DESCRIPTION
		"Reserved."
	::= { fanModule5 3 }

fanModule5State                          OBJECT IDENTIFIER ::= { fanModule5 4 }

fanModule5StateSlotNum                   OBJECT-TYPE
	SYNTAX     Integer32
	MAX-ACCESS read-only
	STATUS     current
	DESCRIPTION
		"This shows the number of installed slots of fan module5."
	::= { fanModule5State 1 }

fanModule5StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module5."
	::= { fanModule5State 2 }

fanModule5StateHealth                    OBJECT-TYPE
	SYNTAX     INTEGER {
		normal(1), fail(2), unknown(3)
	}
	MAX-ACCESS read-only
	STATUS     current
	DESCRIPTION
		"This shows the health state of fan module5."
	::= { fanModule5State 3 }

fanModule5StateRedundancy                OBJECT-TYPE
	SYNTAX     INTEGER {
		redundancy(1), non-redundancy(2), unknown(3)
	}
	MAX-ACCESS read-only
	STATUS     current
	DESCRIPTION
		"This shows the redundancy of fan module5."
	::= { fanModule5State 4 }

fanModule5StateAirVolume                 OBJECT-TYPE
	SYNTAX     Integer32
	UNITS      "0.1 m^3/min"
	MAX-ACCESS read-only
	STATUS     current
	DESCRIPTION
		"This shows the current air volume of fan module5."
	::= { fanModule5State 5 }

fanModule5StateLEDTable                  OBJECT-TYPE
	SYNTAX SEQUENCE OF fanModule5StateLEDEntry
	MAX-ACCESS not-accessible
	STATUS     current
	DESCRIPTION
		"This shows the table of LED of fan module5."
	::= { fanModule5State 6 }

fanModule5StateLEDEntry                  OBJECT-TYPE
	SYNTAX     FanModule5StateLEDEntry
	MAX-ACCESS not-accessible
	STATUS     current
	DESCRIPTION
		"This shows the entry of LED of fan module5."
	INDEX { fanModule5StateLEDIndex }
	::= { fanModule5StateLEDTable 1 }

FanModule5StateLEDEntry ::= SEQUENCE {
	fanModule5StateLEDIndex
		Integer32,
	fanModule5StateLEDName
		DisplayString,
	fanModule5StateLEDType
		DisplayString,
	fanModule5StateLEDState
		INTEGER,
	fanModule5StateLEDColor
		INTEGER
}

fanModule5StateLEDIndex                  OBJECT-TYPE
	SYNTAX     Integer32
	MAX-ACCESS read-only
	STATUS     current
	DESCRIPTION
		"This shows the index of LED of fan module5."
	::= { fanModule5StateLEDEntry 1 }

fanModule5StateLEDName                   OBJECT-TYPE
	SYNTAX     DisplayString
	MAX-ACCESS read-only
	STATUS     current
	DESCRIPTION
		"This shows the name of LED of fan module5."
	::= { fanModule5StateLEDEntry 2 }

fanModule5StateLEDType                   OBJECT-TYPE
	SYNTAX     DisplayString
	MAX-ACCESS read-only
	STATUS     current
	DESCRIPTION
		"Reserved."
	::= { fanModule5StateLEDEntry 3 }

fanModule5StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module5."
	::= { fanModule5StateLEDEntry 4 }

fanModule5StateLEDColor                  OBJECT-TYPE
	SYNTAX     INTEGER {
		blue(1), green(2), red(3), amber(4), unknown(5)
	}
	MAX-ACCESS read-only
	STATUS     current
	DESCRIPTION
		"This shows the color of LED of fan module5."
	::= { fanModule5StateLEDEntry 5 }

fanModule5StateFanTable                  OBJECT-TYPE
	SYNTAX SEQUENCE OF fanModule5StateFanEntry
	MAX-ACCESS not-accessible
	STATUS     current
	DESCRIPTION
		"This shows the table of fan of fan module5."
	::= { fanModule5State 10 }

fanModule5StateFanEntry                  OBJECT-TYPE
	SYNTAX     FanModule5StateFanEntry
	MAX-ACCESS not-accessible
	STATUS     current
	DESCRIPTION
		"This shows the entry of fan of fan module5."
	INDEX { fanModule5StateFanIndex }
	::= { fanModule5StateFanTable 1 }

FanModule5StateFanEntry ::= SEQUENCE {
	fanModule5StateFanIndex
		Integer32,
	fanModule5StateFanLocation
		DisplayString,
	fanModule5StateFanRPM
		Integer32,
	fanModule5StateFanRPMValid
		INTEGER
}

fanModule5StateFanIndex                  OBJECT-TYPE
	SYNTAX     Integer32
	MAX-ACCESS read-only
	STATUS     current
	DESCRIPTION
		"This shows the index of fan of fan module5."
	::= { fanModule5StateFanEntry 1 }

fanModule5StateFanLocation               OBJECT-TYPE
	SYNTAX     DisplayString
	MAX-ACCESS read-only
	STATUS     current
	DESCRIPTION
		"This shows the location of fan of fan module5."
	::= { fanModule5StateFanEntry 2 }

fanModule5StateFanRPM                    OBJECT-TYPE
	SYNTAX     Integer32
	UNITS      "rpm"
	MAX-ACCESS read-only
	STATUS     current
	DESCRIPTION
		"This shows the rpm value of fan module5."
	::= { fanModule5StateFanEntry 3 }

fanModule5StateFanRPMValid               OBJECT-TYPE
	SYNTAX     INTEGER {
		invalid(1), valid(2), unknown(3)
	}
	MAX-ACCESS read-only
	STATUS     current
	DESCRIPTION
		"This shows the validity of fan rpm value of fan module5."
	::= { fanModule5StateFanEntry 4 }

fanModule6                               OBJECT IDENTIFIER ::= { fanModule 6 }

fanModule6BasicInfo                      OBJECT IDENTIFIER ::= { fanModule6 1 }

fanModule6InfoType                       OBJECT-TYPE
	SYNTAX     DisplayString
	MAX-ACCESS read-only
	STATUS     current
	DESCRIPTION
		"This shows the type of fan module6."
	::= { fanModule6BasicInfo 1 }

fanModule6InfoProductName                OBJECT-TYPE
	SYNTAX     DisplayString
	MAX-ACCESS read-only
	STATUS     current
	DESCRIPTION
		"Reserved."
	::= { fanModule6BasicInfo 2 }

fanModule6InfoModel                      OBJECT-TYPE
	SYNTAX     DisplayString
	MAX-ACCESS read-only
	STATUS     current
	DESCRIPTION
		"Reserved."
	::= { fanModule6BasicInfo 3 }

fanModule6InfoSerialNum                  OBJECT-TYPE
	SYNTAX     DisplayString
	MAX-ACCESS read-only
	STATUS     current
	DESCRIPTION
		"Reserved."
	::= { fanModule6BasicInfo 4 }

fanModule6InfoProductVersion             OBJECT-TYPE
	SYNTAX     DisplayString
	MAX-ACCESS read-only
	STATUS     current
	DESCRIPTION
		"Reserved."
	::= { fanModule6BasicInfo 5 }

fanModule6InfoProductManufacturer        OBJECT-TYPE
	SYNTAX     DisplayString
	MAX-ACCESS read-only
	STATUS     current
	DESCRIPTION
		"Reserved."
	::= { fanModule6BasicInfo 6 }

fanModule6InfoBoardProductName           OBJECT-TYPE
	SYNTAX     DisplayString
	MAX-ACCESS read-only
	STATUS     current
	DESCRIPTION
		"Reserved."
	::= { fanModule6BasicInfo 7 }

fanModule6InfoBoardSerialNum             OBJECT-TYPE
	SYNTAX     DisplayString
	MAX-ACCESS read-only
	STATUS     current
	DESCRIPTION
		"Reserved."
	::= { fanModule6BasicInfo 8 }

fanModule6InfoBoardManufacturer          OBJECT-TYPE
	SYNTAX     DisplayString
	MAX-ACCESS read-only
	STATUS     current
	DESCRIPTION
		"Reserved."
	::= { fanModule6BasicInfo 9 }

fanModule6InfoSpec                       OBJECT IDENTIFIER ::= { fanModule6BasicInfo 20 }

fanModule6SpecMaxRPM                     OBJECT-TYPE
	SYNTAX     Integer32
	UNITS      "rpm"
	MAX-ACCESS read-only
	STATUS     current
	DESCRIPTION
		"This shows the maximum rpm of fan module6."
	::= { fanModule6InfoSpec 1 }

fanModule6SpecMaxAirVolume               OBJECT-TYPE
	SYNTAX     Integer32
	UNITS      "0.1 m^3/min"
	MAX-ACCESS read-only
	STATUS     current
	DESCRIPTION
		"This shows the maximum air volume of fan module6."
	::= { fanModule6InfoSpec 2 }

fanModule6SpecMinRPM                     OBJECT-TYPE
	SYNTAX     Integer32
	UNITS      "rpm"
	MAX-ACCESS read-only
	STATUS     current
	DESCRIPTION
		"This shows the minimum rpm of fan module6."
	::= { fanModule6InfoSpec 3 }

fanModule6SpecMinAirVolume               OBJECT-TYPE
	SYNTAX     Integer32
	UNITS      "0.1 m^3/min"
	MAX-ACCESS read-only
	STATUS     current
	DESCRIPTION
		"This shows the minimum air volume of fan module6."
	::= { fanModule6InfoSpec 4 }

fanModule6Capacity                       OBJECT IDENTIFIER ::= { fanModule6 2 }

fanModule6CapacityFan                    OBJECT-TYPE
	SYNTAX     Integer32
	MAX-ACCESS read-only
	STATUS     current
	DESCRIPTION
		"This shows the capacity of fans of fan module6."
	::= { fanModule6Capacity 1 }

fanModule6Settings                       OBJECT-TYPE
	SYNTAX     DisplayString
	MAX-ACCESS read-only
	STATUS     current
	DESCRIPTION
		"Reserved."
	::= { fanModule6 3 }

fanModule6State                          OBJECT IDENTIFIER ::= { fanModule6 4 }

fanModule6StateSlotNum                   OBJECT-TYPE
	SYNTAX     Integer32
	MAX-ACCESS read-only
	STATUS     current
	DESCRIPTION
		"This shows the number of installed slots of fan module6."
	::= { fanModule6State 1 }

fanModule6StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module6."
	::= { fanModule6State 2 }

fanModule6StateHealth                    OBJECT-TYPE
	SYNTAX     INTEGER {
		normal(1), fail(2), unknown(3)
	}
	MAX-ACCESS read-only
	STATUS     current
	DESCRIPTION
		"This shows the health state of fan module6."
	::= { fanModule6State 3 }

fanModule6StateRedundancy                OBJECT-TYPE
	SYNTAX     INTEGER {
		redundancy(1), non-redundancy(2), unknown(3)
	}
	MAX-ACCESS read-only
	STATUS     current
	DESCRIPTION
		"This shows the redundancy of fan module6."
	::= { fanModule6State 4 }

fanModule6StateAirVolume                 OBJECT-TYPE
	SYNTAX     Integer32
	UNITS      "0.1 m^3/min"
	MAX-ACCESS read-only
	STATUS     current
	DESCRIPTION
		"This shows the current air volume of fan module6."
	::= { fanModule6State 5 }

fanModule6StateLEDTable                  OBJECT-TYPE
	SYNTAX SEQUENCE OF fanModule6StateLEDEntry
	MAX-ACCESS not-accessible
	STATUS     current
	DESCRIPTION
		"This shows the table of LED of fan module6."
	::= { fanModule6State 6 }

fanModule6StateLEDEntry                  OBJECT-TYPE
	SYNTAX     FanModule6StateLEDEntry
	MAX-ACCESS not-accessible
	STATUS     current
	DESCRIPTION
		"This shows the entry of LED of fan module6."
	INDEX { fanModule6StateLEDIndex }
	::= { fanModule6StateLEDTable 1 }

FanModule6StateLEDEntry ::= SEQUENCE {
	fanModule6StateLEDIndex
		Integer32,
	fanModule6StateLEDName
		DisplayString,
	fanModule6StateLEDType
		DisplayString,
	fanModule6StateLEDState
		INTEGER,
	fanModule6StateLEDColor
		INTEGER
}

fanModule6StateLEDIndex                  OBJECT-TYPE
	SYNTAX     Integer32
	MAX-ACCESS read-only
	STATUS     current
	DESCRIPTION
		"This shows the index of LED of fan module6."
	::= { fanModule6StateLEDEntry 1 }

fanModule6StateLEDName                   OBJECT-TYPE
	SYNTAX     DisplayString
	MAX-ACCESS read-only
	STATUS     current
	DESCRIPTION
		"This shows the name of LED of fan module6."
	::= { fanModule6StateLEDEntry 2 }

fanModule6StateLEDType                   OBJECT-TYPE
	SYNTAX     DisplayString
	MAX-ACCESS read-only
	STATUS     current
	DESCRIPTION
		"Reserved."
	::= { fanModule6StateLEDEntry 3 }

fanModule6StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module6."
	::= { fanModule6StateLEDEntry 4 }

fanModule6StateLEDColor                  OBJECT-TYPE
	SYNTAX     INTEGER {
		blue(1), green(2), red(3), amber(4), unknown(5)
	}
	MAX-ACCESS read-only
	STATUS     current
	DESCRIPTION
		"This shows the color of LED of fan module6."
	::= { fanModule6StateLEDEntry 5 }

fanModule6StateFanTable                  OBJECT-TYPE
	SYNTAX SEQUENCE OF fanModule6StateFanEntry
	MAX-ACCESS not-accessible
	STATUS     current
	DESCRIPTION
		"This shows the table of fan of fan module6."
	::= { fanModule6State 10 }

fanModule6StateFanEntry                  OBJECT-TYPE
	SYNTAX     FanModule6StateFanEntry
	MAX-ACCESS not-accessible
	STATUS     current
	DESCRIPTION
		"This shows the entry of fan of fan module6."
	INDEX { fanModule6StateFanIndex }
	::= { fanModule6StateFanTable 1 }

FanModule6StateFanEntry ::= SEQUENCE {
	fanModule6StateFanIndex
		Integer32,
	fanModule6StateFanLocation
		DisplayString,
	fanModule6StateFanRPM
		Integer32,
	fanModule6StateFanRPMValid
		INTEGER
}

fanModule6StateFanIndex                  OBJECT-TYPE
	SYNTAX     Integer32
	MAX-ACCESS read-only
	STATUS     current
	DESCRIPTION
		"This shows the index of fan of fan module6."
	::= { fanModule6StateFanEntry 1 }

fanModule6StateFanLocation               OBJECT-TYPE
	SYNTAX     DisplayString
	MAX-ACCESS read-only
	STATUS     current
	DESCRIPTION
		"This shows the location of fan of fan module6."
	::= { fanModule6StateFanEntry 2 }

fanModule6StateFanRPM                    OBJECT-TYPE
	SYNTAX     Integer32
	UNITS      "rpm"
	MAX-ACCESS read-only
	STATUS     current
	DESCRIPTION
		"This shows the rpm value of fan module6."
	::= { fanModule6StateFanEntry 3 }

fanModule6StateFanRPMValid               OBJECT-TYPE
	SYNTAX     INTEGER {
		invalid(1), valid(2), unknown(3)
	}
	MAX-ACCESS read-only
	STATUS     current
	DESCRIPTION
		"This shows the validity of fan rpm value of fan module6."
	::= { fanModule6StateFanEntry 4 }

fanModule7                               OBJECT IDENTIFIER ::= { fanModule 7 }

fanModule7BasicInfo                      OBJECT IDENTIFIER ::= { fanModule7 1 }

fanModule7InfoType                       OBJECT-TYPE
	SYNTAX     DisplayString
	MAX-ACCESS read-only
	STATUS     current
	DESCRIPTION
		"This shows the type of fan module7."
	::= { fanModule7BasicInfo 1 }

fanModule7InfoProductName                OBJECT-TYPE
	SYNTAX     DisplayString
	MAX-ACCESS read-only
	STATUS     current
	DESCRIPTION
		"Reserved."
	::= { fanModule7BasicInfo 2 }

fanModule7InfoModel                      OBJECT-TYPE
	SYNTAX     DisplayString
	MAX-ACCESS read-only
	STATUS     current
	DESCRIPTION
		"Reserved."
	::= { fanModule7BasicInfo 3 }

fanModule7InfoSerialNum                  OBJECT-TYPE
	SYNTAX     DisplayString
	MAX-ACCESS read-only
	STATUS     current
	DESCRIPTION
		"Reserved."
	::= { fanModule7BasicInfo 4 }

fanModule7InfoProductVersion             OBJECT-TYPE
	SYNTAX     DisplayString
	MAX-ACCESS read-only
	STATUS     current
	DESCRIPTION
		"Reserved."
	::= { fanModule7BasicInfo 5 }

fanModule7InfoProductManufacturer        OBJECT-TYPE
	SYNTAX     DisplayString
	MAX-ACCESS read-only
	STATUS     current
	DESCRIPTION
		"Reserved."
	::= { fanModule7BasicInfo 6 }

fanModule7InfoBoardProductName           OBJECT-TYPE
	SYNTAX     DisplayString
	MAX-ACCESS read-only
	STATUS     current
	DESCRIPTION
		"Reserved."
	::= { fanModule7BasicInfo 7 }

fanModule7InfoBoardSerialNum             OBJECT-TYPE
	SYNTAX     DisplayString
	MAX-ACCESS read-only
	STATUS     current
	DESCRIPTION
		"Reserved."
	::= { fanModule7BasicInfo 8 }

fanModule7InfoBoardManufacturer          OBJECT-TYPE
	SYNTAX     DisplayString
	MAX-ACCESS read-only
	STATUS     current
	DESCRIPTION
		"Reserved."
	::= { fanModule7BasicInfo 9 }

fanModule7InfoSpec                       OBJECT IDENTIFIER ::= { fanModule7BasicInfo 20 }

fanModule7SpecMaxRPM                     OBJECT-TYPE
	SYNTAX     Integer32
	UNITS      "rpm"
	MAX-ACCESS read-only
	STATUS     current
	DESCRIPTION
		"This shows the maximum rpm of fan module7."
	::= { fanModule7InfoSpec 1 }

fanModule7SpecMaxAirVolume               OBJECT-TYPE
	SYNTAX     Integer32
	UNITS      "0.1 m^3/min"
	MAX-ACCESS read-only
	STATUS     current
	DESCRIPTION
		"This shows the maximum air volume of fan module7."
	::= { fanModule7InfoSpec 2 }

fanModule7SpecMinRPM                     OBJECT-TYPE
	SYNTAX     Integer32
	UNITS      "rpm"
	MAX-ACCESS read-only
	STATUS     current
	DESCRIPTION
		"This shows the minimum rpm of fan module7."
	::= { fanModule7InfoSpec 3 }

fanModule7SpecMinAirVolume               OBJECT-TYPE
	SYNTAX     Integer32
	UNITS      "0.1 m^3/min"
	MAX-ACCESS read-only
	STATUS     current
	DESCRIPTION
		"This shows the minimum air volume of fan module7."
	::= { fanModule7InfoSpec 4 }

fanModule7Capacity                       OBJECT IDENTIFIER ::= { fanModule7 2 }

fanModule7CapacityFan                    OBJECT-TYPE
	SYNTAX     Integer32
	MAX-ACCESS read-only
	STATUS     current
	DESCRIPTION
		"This shows the capacity of fans of fan module7."
	::= { fanModule7Capacity 1 }

fanModule7Settings                       OBJECT-TYPE
	SYNTAX     DisplayString
	MAX-ACCESS read-only
	STATUS     current
	DESCRIPTION
		"Reserved."
	::= { fanModule7 3 }

fanModule7State                          OBJECT IDENTIFIER ::= { fanModule7 4 }

fanModule7StateSlotNum                   OBJECT-TYPE
	SYNTAX     Integer32
	MAX-ACCESS read-only
	STATUS     current
	DESCRIPTION
		"This shows the number of installed slots of fan module7."
	::= { fanModule7State 1 }

fanModule7StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module7."
	::= { fanModule7State 2 }

fanModule7StateHealth                    OBJECT-TYPE
	SYNTAX     INTEGER {
		normal(1), fail(2), unknown(3)
	}
	MAX-ACCESS read-only
	STATUS     current
	DESCRIPTION
		"This shows the health state of fan module7."
	::= { fanModule7State 3 }

fanModule7StateRedundancy                OBJECT-TYPE
	SYNTAX     INTEGER {
		redundancy(1), non-redundancy(2), unknown(3)
	}
	MAX-ACCESS read-only
	STATUS     current
	DESCRIPTION
		"This shows the redundancy of fan module7."
	::= { fanModule7State 4 }

fanModule7StateAirVolume                 OBJECT-TYPE
	SYNTAX     Integer32
	UNITS      "0.1 m^3/min"
	MAX-ACCESS read-only
	STATUS     current
	DESCRIPTION
		"This shows the current air volume of fan module7."
	::= { fanModule7State 5 }

fanModule7StateLEDTable                  OBJECT-TYPE
	SYNTAX SEQUENCE OF fanModule7StateLEDEntry
	MAX-ACCESS not-accessible
	STATUS     current
	DESCRIPTION
		"This shows the table of LED of fan module7."
	::= { fanModule7State 6 }

fanModule7StateLEDEntry                  OBJECT-TYPE
	SYNTAX     FanModule7StateLEDEntry
	MAX-ACCESS not-accessible
	STATUS     current
	DESCRIPTION
		"This shows the entry of LED of fan module7."
	INDEX { fanModule7StateLEDIndex }
	::= { fanModule7StateLEDTable 1 }

FanModule7StateLEDEntry ::= SEQUENCE {
	fanModule7StateLEDIndex
		Integer32,
	fanModule7StateLEDName
		DisplayString,
	fanModule7StateLEDType
		DisplayString,
	fanModule7StateLEDState
		INTEGER,
	fanModule7StateLEDColor
		INTEGER
}

fanModule7StateLEDIndex                  OBJECT-TYPE
	SYNTAX     Integer32
	MAX-ACCESS read-only
	STATUS     current
	DESCRIPTION
		"This shows the index of LED of fan module7."
	::= { fanModule7StateLEDEntry 1 }

fanModule7StateLEDName                   OBJECT-TYPE
	SYNTAX     DisplayString
	MAX-ACCESS read-only
	STATUS     current
	DESCRIPTION
		"This shows the name of LED of fan module7."
	::= { fanModule7StateLEDEntry 2 }

fanModule7StateLEDType                   OBJECT-TYPE
	SYNTAX     DisplayString
	MAX-ACCESS read-only
	STATUS     current
	DESCRIPTION
		"Reserved."
	::= { fanModule7StateLEDEntry 3 }

fanModule7StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module7."
	::= { fanModule7StateLEDEntry 4 }

fanModule7StateLEDColor                  OBJECT-TYPE
	SYNTAX     INTEGER {
		blue(1), green(2), red(3), amber(4), unknown(5)
	}
	MAX-ACCESS read-only
	STATUS     current
	DESCRIPTION
		"This shows the color of LED of fan module7."
	::= { fanModule7StateLEDEntry 5 }

fanModule7StateFanTable                  OBJECT-TYPE
	SYNTAX SEQUENCE OF fanModule7StateFanEntry
	MAX-ACCESS not-accessible
	STATUS     current
	DESCRIPTION
		"This shows the table of fan of fan module7."
	::= { fanModule7State 10 }

fanModule7StateFanEntry                  OBJECT-TYPE
	SYNTAX     FanModule7StateFanEntry
	MAX-ACCESS not-accessible
	STATUS     current
	DESCRIPTION
		"This shows the entry of fan of fan module7."
	INDEX { fanModule7StateFanIndex }
	::= { fanModule7StateFanTable 1 }

FanModule7StateFanEntry ::= SEQUENCE {
	fanModule7StateFanIndex
		Integer32,
	fanModule7StateFanLocation
		DisplayString,
	fanModule7StateFanRPM
		Integer32,
	fanModule7StateFanRPMValid
		INTEGER
}

fanModule7StateFanIndex                  OBJECT-TYPE
	SYNTAX     Integer32
	MAX-ACCESS read-only
	STATUS     current
	DESCRIPTION
		"This shows the index of fan of fan module7."
	::= { fanModule7StateFanEntry 1 }

fanModule7StateFanLocation               OBJECT-TYPE
	SYNTAX     DisplayString
	MAX-ACCESS read-only
	STATUS     current
	DESCRIPTION
		"This shows the location of fan of fan module7."
	::= { fanModule7StateFanEntry 2 }

fanModule7StateFanRPM                    OBJECT-TYPE
	SYNTAX     Integer32
	UNITS      "rpm"
	MAX-ACCESS read-only
	STATUS     current
	DESCRIPTION
		"This shows the rpm value of fan module7."
	::= { fanModule7StateFanEntry 3 }

fanModule7StateFanRPMValid               OBJECT-TYPE
	SYNTAX     INTEGER {
		invalid(1), valid(2), unknown(3)
	}
	MAX-ACCESS read-only
	STATUS     current
	DESCRIPTION
		"This shows the validity of fan rpm value of fan module7."
	::= { fanModule7StateFanEntry 4 }

fanModule8                               OBJECT IDENTIFIER ::= { fanModule 8 }

fanModule8BasicInfo                      OBJECT IDENTIFIER ::= { fanModule8 1 }

fanModule8InfoType                       OBJECT-TYPE
	SYNTAX     DisplayString
	MAX-ACCESS read-only
	STATUS     current
	DESCRIPTION
		"This shows the type of fan module8."
	::= { fanModule8BasicInfo 1 }

fanModule8InfoProductName                OBJECT-TYPE
	SYNTAX     DisplayString
	MAX-ACCESS read-only
	STATUS     current
	DESCRIPTION
		"Reserved."
	::= { fanModule8BasicInfo 2 }

fanModule8InfoModel                      OBJECT-TYPE
	SYNTAX     DisplayString
	MAX-ACCESS read-only
	STATUS     current
	DESCRIPTION
		"Reserved."
	::= { fanModule8BasicInfo 3 }

fanModule8InfoSerialNum                  OBJECT-TYPE
	SYNTAX     DisplayString
	MAX-ACCESS read-only
	STATUS     current
	DESCRIPTION
		"Reserved."
	::= { fanModule8BasicInfo 4 }

fanModule8InfoProductVersion             OBJECT-TYPE
	SYNTAX     DisplayString
	MAX-ACCESS read-only
	STATUS     current
	DESCRIPTION
		"Reserved."
	::= { fanModule8BasicInfo 5 }

fanModule8InfoProductManufacturer        OBJECT-TYPE
	SYNTAX     DisplayString
	MAX-ACCESS read-only
	STATUS     current
	DESCRIPTION
		"Reserved."
	::= { fanModule8BasicInfo 6 }

fanModule8InfoBoardProductName           OBJECT-TYPE
	SYNTAX     DisplayString
	MAX-ACCESS read-only
	STATUS     current
	DESCRIPTION
		"Reserved."
	::= { fanModule8BasicInfo 7 }

fanModule8InfoBoardSerialNum             OBJECT-TYPE
	SYNTAX     DisplayString
	MAX-ACCESS read-only
	STATUS     current
	DESCRIPTION
		"Reserved."
	::= { fanModule8BasicInfo 8 }

fanModule8InfoBoardManufacturer          OBJECT-TYPE
	SYNTAX     DisplayString
	MAX-ACCESS read-only
	STATUS     current
	DESCRIPTION
		"Reserved."
	::= { fanModule8BasicInfo 9 }

fanModule8InfoSpec                       OBJECT IDENTIFIER ::= { fanModule8BasicInfo 20 }

fanModule8SpecMaxRPM                     OBJECT-TYPE
	SYNTAX     Integer32
	UNITS      "rpm"
	MAX-ACCESS read-only
	STATUS     current
	DESCRIPTION
		"This shows the maximum rpm of fan module8."
	::= { fanModule8InfoSpec 1 }

fanModule8SpecMaxAirVolume               OBJECT-TYPE
	SYNTAX     Integer32
	UNITS      "0.1 m^3/min"
	MAX-ACCESS read-only
	STATUS     current
	DESCRIPTION
		"This shows the maximum air volume of fan module8."
	::= { fanModule8InfoSpec 2 }

fanModule8SpecMinRPM                     OBJECT-TYPE
	SYNTAX     Integer32
	UNITS      "rpm"
	MAX-ACCESS read-only
	STATUS     current
	DESCRIPTION
		"This shows the minimum rpm of fan module8."
	::= { fanModule8InfoSpec 3 }

fanModule8SpecMinAirVolume               OBJECT-TYPE
	SYNTAX     Integer32
	UNITS      "0.1 m^3/min"
	MAX-ACCESS read-only
	STATUS     current
	DESCRIPTION
		"This shows the minimum air volume of fan module8."
	::= { fanModule8InfoSpec 4 }

fanModule8Capacity                       OBJECT IDENTIFIER ::= { fanModule8 2 }

fanModule8CapacityFan                    OBJECT-TYPE
	SYNTAX     Integer32
	MAX-ACCESS read-only
	STATUS     current
	DESCRIPTION
		"This shows the capacity of fans of fan module8."
	::= { fanModule8Capacity 1 }

fanModule8Settings                       OBJECT-TYPE
	SYNTAX     DisplayString
	MAX-ACCESS read-only
	STATUS     current
	DESCRIPTION
		"Reserved."
	::= { fanModule8 3 }

fanModule8State                          OBJECT IDENTIFIER ::= { fanModule8 4 }

fanModule8StateSlotNum                   OBJECT-TYPE
	SYNTAX     Integer32
	MAX-ACCESS read-only
	STATUS     current
	DESCRIPTION
		"This shows the number of installed slots of fan module8."
	::= { fanModule8State 1 }

fanModule8StatePower                     OBJECT-TYPE
	SYNTAX     INTEGER {
		poweroff(1), standby(2), poweron(3), unknown(4), poweron-executing(5), poweroff-executing(6)
	}
	MAX-ACCESS read-only
	STATUS     current
	DESCRIPTION
		"This shows the power supply state of fan module8."
	::= { fanModule8State 2 }

fanModule8StateHealth                    OBJECT-TYPE
	SYNTAX     INTEGER {
		normal(1), fail(2), unknown(3)
	}
	MAX-ACCESS read-only
	STATUS     current
	DESCRIPTION
		"This shows the health state of fan module8."
	::= { fanModule8State 3 }

fanModule8StateRedundancy                OBJECT-TYPE
	SYNTAX     INTEGER {
		redundancy(1), non-redundancy(2), unknown(3)
	}
	MAX-ACCESS read-only
	STATUS     current
	DESCRIPTION
		"This shows the redundancy of fan module8."
	::= { fanModule8State 4 }

fanModule8StateAirVolume                 OBJECT-TYPE
	SYNTAX     Integer32
	UNITS      "0.1 m^3/min"
	MAX-ACCESS read-only
	STATUS     current
	DESCRIPTION
		"This shows the current air volume of fan module8."
	::= { fanModule8State 5 }

fanModule8StateLEDTable                  OBJECT-TYPE
	SYNTAX SEQUENCE OF fanModule8StateLEDEntry
	MAX-ACCESS not-accessible
	STATUS     current
	DESCRIPTION
		"This shows the table of LED of fan module8."
	::= { fanModule8State 6 }

fanModule8StateLEDEntry                  OBJECT-TYPE
	SYNTAX     FanModule8StateLEDEntry
	MAX-ACCESS not-accessible
	STATUS     current
	DESCRIPTION
		"This shows the entry of LED of fan module8."
	INDEX { fanModule8StateLEDIndex }
	::= { fanModule8StateLEDTable 1 }

FanModule8StateLEDEntry ::= SEQUENCE {
	fanModule8StateLEDIndex
		Integer32,
	fanModule8StateLEDName
		DisplayString,
	fanModule8StateLEDType
		DisplayString,
	fanModule8StateLEDState
		INTEGER,
	fanModule8StateLEDColor
		INTEGER
}

fanModule8StateLEDIndex                  OBJECT-TYPE
	SYNTAX     Integer32
	MAX-ACCESS read-only
	STATUS     current
	DESCRIPTION
		"This shows the index of LED of fan module8."
	::= { fanModule8StateLEDEntry 1 }

fanModule8StateLEDName                   OBJECT-TYPE
	SYNTAX     DisplayString
	MAX-ACCESS read-only
	STATUS     current
	DESCRIPTION
		"This shows the name of LED of fan module8."
	::= { fanModule8StateLEDEntry 2 }

fanModule8StateLEDType                   OBJECT-TYPE
	SYNTAX     DisplayString
	MAX-ACCESS read-only
	STATUS     current
	DESCRIPTION
		"Reserved."
	::= { fanModule8StateLEDEntry 3 }

fanModule8StateLEDState                  OBJECT-TYPE
	SYNTAX     INTEGER {
		turn-off(1), turn-on(2), unknown(3), blink(4), blink-fast(5), blink-slow(6)
	}
	MAX-ACCESS read-only
	STATUS     current
	DESCRIPTION
		"This shows the state of LED of fan module8."
	::= { fanModule8StateLEDEntry 4 }

fanModule8StateLEDColor                  OBJECT-TYPE
	SYNTAX     INTEGER {
		blue(1), green(2), red(3), amber(4), unknown(5)
	}
	MAX-ACCESS read-only
	STATUS     current
	DESCRIPTION
		"This shows the color of LED of fan module8."
	::= { fanModule8StateLEDEntry 5 }

fanModule8StateFanTable                  OBJECT-TYPE
	SYNTAX SEQUENCE OF fanModule8StateFanEntry
	MAX-ACCESS not-accessible
	STATUS     current
	DESCRIPTION
		"This shows the table of fan of fan module8."
	::= { fanModule8State 10 }

fanModule8StateFanEntry                  OBJECT-TYPE
	SYNTAX     FanModule8StateFanEntry
	MAX-ACCESS not-accessible
	STATUS     current
	DESCRIPTION
		"This shows the entry of fan of fan module8."
	INDEX { fanModule8StateFanIndex }
	::= { fanModule8StateFanTable 1 }

FanModule8StateFanEntry ::= SEQUENCE {
	fanModule8StateFanIndex
		Integer32,
	fanModule8StateFanLocation
		DisplayString,
	fanModule8StateFanRPM
		Integer32,
	fanModule8StateFanRPMValid
		INTEGER
}

fanModule8StateFanIndex                  OBJECT-TYPE
	SYNTAX     Integer32
	MAX-ACCESS read-only
	STATUS     current
	DESCRIPTION
		"This shows the index of fan of fan module8."
	::= { fanModule8StateFanEntry 1 }

fanModule8StateFanLocation               OBJECT-TYPE
	SYNTAX     DisplayString
	MAX-ACCESS read-only
	STATUS     current
	DESCRIPTION
		"This shows the location of fan of fan module8."
	::= { fanModule8StateFanEntry 2 }

fanModule8StateFanRPM                    OBJECT-TYPE
	SYNTAX     Integer32
	UNITS      "rpm"
	MAX-ACCESS read-only
	STATUS     current
	DESCRIPTION
		"This shows the rpm value of fan module8."
	::= { fanModule8StateFanEntry 3 }

fanModule8StateFanRPMValid               OBJECT-TYPE
	SYNTAX     INTEGER {
		invalid(1), valid(2), unknown(3)
	}
	MAX-ACCESS read-only
	STATUS     current
	DESCRIPTION
		"This shows the validity of fan rpm value of fan module8."
	::= { fanModule8StateFanEntry 4 }

powerSupply                              OBJECT IDENTIFIER ::= { component 2 }

powerSupply1                             OBJECT IDENTIFIER ::= { powerSupply 1 }

powerSupply1BasicInfo                    OBJECT IDENTIFIER ::= { powerSupply1 1 }

powerSupply1InfoType                     OBJECT-TYPE
	SYNTAX     DisplayString
	MAX-ACCESS read-only
	STATUS     current
	DESCRIPTION
		"Reserved."
	::= { powerSupply1BasicInfo 1 }

powerSupply1InfoProductName              OBJECT-TYPE
	SYNTAX     DisplayString
	MAX-ACCESS read-only
	STATUS     current
	DESCRIPTION
		"This shows the product name of power supply module1."
	::= { powerSupply1BasicInfo 2 }

powerSupply1InfoModel                    OBJECT-TYPE
	SYNTAX     DisplayString
	MAX-ACCESS read-only
	STATUS     current
	DESCRIPTION
		"This shows the model name of power supply module1."
	::= { powerSupply1BasicInfo 3 }

powerSupply1InfoSerialNum                OBJECT-TYPE
	SYNTAX     DisplayString
	MAX-ACCESS read-only
	STATUS     current
	DESCRIPTION
		"This shows the serial number of power supply module1."
	::= { powerSupply1BasicInfo 4 }

powerSupply1InfoProductVersion           OBJECT-TYPE
	SYNTAX     DisplayString
	MAX-ACCESS read-only
	STATUS     current
	DESCRIPTION
		"This shows the product version of power supply module1."
	::= { powerSupply1BasicInfo 5 }

powerSupply1InfoProductManufacturer      OBJECT-TYPE
	SYNTAX     DisplayString
	MAX-ACCESS read-only
	STATUS     current
	DESCRIPTION
		"This shows the product manufacturer of power supply module1."
	::= { powerSupply1BasicInfo 6 }

powerSupply1InfoBoardProductName         OBJECT-TYPE
	SYNTAX     DisplayString
	MAX-ACCESS read-only
	STATUS     current
	DESCRIPTION
		"Reserved."
	::= { powerSupply1BasicInfo 7 }

powerSupply1InfoBoardSerialNum           OBJECT-TYPE
	SYNTAX     DisplayString
	MAX-ACCESS read-only
	STATUS     current
	DESCRIPTION
		"Reserved."
	::= { powerSupply1BasicInfo 8 }

powerSupply1InfoBoardManufacturer        OBJECT-TYPE
	SYNTAX     DisplayString
	MAX-ACCESS read-only
	STATUS     current
	DESCRIPTION
		"Reserved."
	::= { powerSupply1BasicInfo 9 }

powerSupply1InfoSpec                     OBJECT IDENTIFIER ::= { powerSupply1BasicInfo 20 }

powerSupply1SpecRateVoltageMain          OBJECT-TYPE
	SYNTAX     Integer32
	UNITS      "0.1 V"
	MAX-ACCESS read-only
	STATUS     current
	DESCRIPTION
		"This shows the rated voltage of power supply module1.(main)"
	::= { powerSupply1InfoSpec 1 }

powerSupply1SpecRateVoltageSub           OBJECT-TYPE
	SYNTAX     Integer32
	UNITS      "0.1 V"
	MAX-ACCESS read-only
	STATUS     current
	DESCRIPTION
		"This shows the rated voltage of power supply module1.(sub)"
	::= { powerSupply1InfoSpec 2 }

powerSupply1SpecAmbientTempUpperLimit    OBJECT-TYPE
	SYNTAX     Integer32
	UNITS      "0.1 degrees C"
	MAX-ACCESS read-only
	STATUS     current
	DESCRIPTION
		"This shows the highest temperature of ambient in power supply module."
	::= { powerSupply1InfoSpec 3 }

powerSupply1SpecAmbientTempLowerLimit    OBJECT-TYPE
	SYNTAX     Integer32
	UNITS      "0.1 degrees C"
	MAX-ACCESS read-only
	STATUS     current
	DESCRIPTION
		"This shows the lowest temperature of ambient in power supply module."
	::= { powerSupply1InfoSpec 4 }

powerSupply1SpecHotSpotTempUpperLimit    OBJECT-TYPE
	SYNTAX     Integer32
	UNITS      "0.1 degrees C"
	MAX-ACCESS read-only
	STATUS     current
	DESCRIPTION
		"This shows the highest temperature of hot spot in power supply module."
	::= { powerSupply1InfoSpec 5 }

powerSupply1SpecHotSpotTempLowerLimit    OBJECT-TYPE
	SYNTAX     Integer32
	UNITS      "0.1 degrees C"
	MAX-ACCESS read-only
	STATUS     current
	DESCRIPTION
		"This shows the lowest temperature of hot spot in power supply module."
	::= { powerSupply1InfoSpec 6 }

powerSupply1SpecExhaustTempUpperLimit    OBJECT-TYPE
	SYNTAX     Integer32
	UNITS      "0.1 degrees C"
	MAX-ACCESS read-only
	STATUS     current
	DESCRIPTION
		"This shows the highest temperature of exhaust in power supply module."
	::= { powerSupply1InfoSpec 7 }

powerSupply1SpecExhaustTempLowerLimit    OBJECT-TYPE
	SYNTAX     Integer32
	UNITS      "0.1 degrees C"
	MAX-ACCESS read-only
	STATUS     current
	DESCRIPTION
		"This shows the lowest temperature of exhaust in power supply module."
	::= { powerSupply1InfoSpec 8 }

powerSupply1Capacity                     OBJECT IDENTIFIER ::= { powerSupply1 2 }

powerSupply1CapacityFan                  OBJECT-TYPE
	SYNTAX     Integer32
	MAX-ACCESS read-only
	STATUS     current
	DESCRIPTION
		"This shows the capacity fans of power supply module1."
	::= { powerSupply1Capacity 1 }

powerSupply1Settings                     OBJECT-TYPE
	SYNTAX     DisplayString
	MAX-ACCESS read-only
	STATUS     current
	DESCRIPTION
		"Reserved."
	::= { powerSupply1 3 }

powerSupply1State                        OBJECT IDENTIFIER ::= { powerSupply1 4 }

powerSupply1StateSlotNum                 OBJECT-TYPE
	SYNTAX     Integer32
	MAX-ACCESS read-only
	STATUS     current
	DESCRIPTION
		"This shows the number of installed slots of power supply module1."
	::= { powerSupply1State 1 }

powerSupply1StatePower                   OBJECT-TYPE
	SYNTAX     INTEGER {
		poweroff(1), poweron(2), unknown(3)
	}
	MAX-ACCESS read-only
	STATUS     current
	DESCRIPTION
		"This shows the power supply state of power supply module1."
	::= { powerSupply1State 2 }

powerSupply1StateHealth                  OBJECT-TYPE
	SYNTAX     INTEGER {
		normal(1), fail(2), unknown(3)
	}
	MAX-ACCESS read-only
	STATUS     current
	DESCRIPTION
		"This shows the health state of power supply module1."
	::= { powerSupply1State 3 }

powerSupply1StateAmbientTemp             OBJECT-TYPE
	SYNTAX     Integer32
	UNITS      "0.1 degrees C"
	MAX-ACCESS read-only
	STATUS     current
	DESCRIPTION
		"This shows the temperature value of ambient sensor of power supply module1."
	::= { powerSupply1State 4 }

powerSupply1StateHotSpotTemp             OBJECT-TYPE
	SYNTAX     Integer32
	UNITS      "0.1 degrees C"
	MAX-ACCESS read-only
	STATUS     current
	DESCRIPTION
		"This shows the temperature value of hot spot sensor of power supply module1."
	::= { powerSupply1State 5 }

powerSupply1StateExhaustTemp             OBJECT-TYPE
	SYNTAX     Integer32
	UNITS      "0.1 degrees C"
	MAX-ACCESS read-only
	STATUS     current
	DESCRIPTION
		"This shows the temperature value of exhaust sensor of power supply module."
	::= { powerSupply1State 6 }

powerSupply1StateMainVoltage             OBJECT-TYPE
	SYNTAX     Integer32
	UNITS      "0.1 V"
	MAX-ACCESS read-only
	STATUS     current
	DESCRIPTION
		"This shows the main voltage of power supply module1."
	::= { powerSupply1State 7 }

powerSupply1StateSubVoltage              OBJECT-TYPE
	SYNTAX     Integer32
	UNITS      "0.1 V"
	MAX-ACCESS read-only
	STATUS     current
	DESCRIPTION
		"This shows the sub voltage of power supply module1."
	::= { powerSupply1State 8 }

powerSupply1StateInputVoltage            OBJECT-TYPE
	SYNTAX     Integer32
	UNITS      "0.1 V"
	MAX-ACCESS read-only
	STATUS     current
	DESCRIPTION
		"This shows the input voltage of power supply module1."
	::= { powerSupply1State 9 }

powerSupply1StateMainCurrent             OBJECT-TYPE
	SYNTAX     Integer32
	UNITS      "0.1 A"
	MAX-ACCESS read-only
	STATUS     current
	DESCRIPTION
		"This shows the main current of power supply module1."
	::= { powerSupply1State 10 }

powerSupply1StateSubCurrent              OBJECT-TYPE
	SYNTAX     Integer32
	UNITS      "0.1 A"
	MAX-ACCESS read-only
	STATUS     current
	DESCRIPTION
		"This shows the sub current of power supply module1."
	::= { powerSupply1State 11 }

powerSupply1StateInputCurrent            OBJECT-TYPE
	SYNTAX     Integer32
	UNITS      "0.1 A"
	MAX-ACCESS read-only
	STATUS     current
	DESCRIPTION
		"This shows the input current of power supply module1."
	::= { powerSupply1State 12 }

powerSupply1StateLEDTable                OBJECT-TYPE
	SYNTAX SEQUENCE OF powerSupply1StateLEDEntry
	MAX-ACCESS not-accessible
	STATUS     current
	DESCRIPTION
		"Reserved."
	::= { powerSupply1State 13 }

powerSupply1StateLEDEntry                OBJECT-TYPE
	SYNTAX     PowerSupply1StateLEDEntry
	MAX-ACCESS not-accessible
	STATUS     current
	DESCRIPTION
		"Reserved."
	INDEX { powerSupply1StateLEDIndex }
	::= { powerSupply1StateLEDTable 1 }

PowerSupply1StateLEDEntry ::= SEQUENCE {
	powerSupply1StateLEDIndex
		Integer32,
	powerSupply1StateLEDName
		DisplayString,
	powerSupply1StateLEDType
		DisplayString,
	powerSupply1StateLEDState
		DisplayString,
	powerSupply1StateLEDColor
		DisplayString
}

powerSupply1StateLEDIndex                OBJECT-TYPE
	SYNTAX     Integer32
	MAX-ACCESS read-only
	STATUS     current
	DESCRIPTION
		"Reserved."
	::= { powerSupply1StateLEDEntry 1 }

powerSupply1StateLEDName                 OBJECT-TYPE
	SYNTAX     DisplayString
	MAX-ACCESS read-only
	STATUS     current
	DESCRIPTION
		"Reserved."
	::= { powerSupply1StateLEDEntry 2 }

powerSupply1StateLEDType                 OBJECT-TYPE
	SYNTAX     DisplayString
	MAX-ACCESS read-only
	STATUS     current
	DESCRIPTION
		"Reserved."
	::= { powerSupply1StateLEDEntry 3 }

powerSupply1StateLEDState                OBJECT-TYPE
	SYNTAX     DisplayString
	MAX-ACCESS read-only
	STATUS     current
	DESCRIPTION
		"Reserved."
	::= { powerSupply1StateLEDEntry 4 }

powerSupply1StateLEDColor                OBJECT-TYPE
	SYNTAX     DisplayString
	MAX-ACCESS read-only
	STATUS     current
	DESCRIPTION
		"Reserved."
	::= { powerSupply1StateLEDEntry 5 }

powerSupply1StateFanTable                OBJECT-TYPE
	SYNTAX SEQUENCE OF powerSupply1StateFanEntry
	MAX-ACCESS not-accessible
	STATUS     current
	DESCRIPTION
		"This shows the table of fan of power supply module1."
	::= { powerSupply1State 14 }

powerSupply1StateFanEntry                OBJECT-TYPE
	SYNTAX     PowerSupply1StateFanEntry
	MAX-ACCESS not-accessible
	STATUS     current
	DESCRIPTION
		"This shows the entry of fan of power supply module1."
	INDEX { powerSupply1StateFanIndex }
	::= { powerSupply1StateFanTable 1 }

PowerSupply1StateFanEntry ::= SEQUENCE {
	powerSupply1StateFanIndex
		Integer32,
	powerSupply1StateFanLocation
		DisplayString,
	powerSupply1StateFanRPM
		Integer32
}

powerSupply1StateFanIndex                OBJECT-TYPE
	SYNTAX     Integer32
	MAX-ACCESS read-only
	STATUS     current
	DESCRIPTION
		"This shows the index of fan of power supply module1."
	::= { powerSupply1StateFanEntry 1 }

powerSupply1StateFanLocation             OBJECT-TYPE
	SYNTAX     DisplayString
	MAX-ACCESS read-only
	STATUS     current
	DESCRIPTION
		"This shows the location of fan of power supply module1."
	::= { powerSupply1StateFanEntry 2 }

powerSupply1StateFanRPM                  OBJECT-TYPE
	SYNTAX     Integer32
	UNITS      "rpm"
	MAX-ACCESS read-only
	STATUS     current
	DESCRIPTION
		"This shows the rpm value of power supply module1."
	::= { powerSupply1StateFanEntry 3 }

powerSupply2                             OBJECT IDENTIFIER ::= { powerSupply 2 }

powerSupply2BasicInfo                    OBJECT IDENTIFIER ::= { powerSupply2 1 }

powerSupply2InfoType                     OBJECT-TYPE
	SYNTAX     Integer32
	MAX-ACCESS read-only
	STATUS     current
	DESCRIPTION
		"Reserved."
	::= { powerSupply2BasicInfo 1 }

powerSupply2InfoProductName              OBJECT-TYPE
	SYNTAX     DisplayString
	MAX-ACCESS read-only
	STATUS     current
	DESCRIPTION
		"This shows the product name of power supply module2."
	::= { powerSupply2BasicInfo 2 }

powerSupply2InfoModel                    OBJECT-TYPE
	SYNTAX     DisplayString
	MAX-ACCESS read-only
	STATUS     current
	DESCRIPTION
		"This shows the model name of power supply module2."
	::= { powerSupply2BasicInfo 3 }

powerSupply2InfoSerialNum                OBJECT-TYPE
	SYNTAX     DisplayString
	MAX-ACCESS read-only
	STATUS     current
	DESCRIPTION
		"This shows the serial number of power supply module2."
	::= { powerSupply2BasicInfo 4 }

powerSupply2InfoProductVersion           OBJECT-TYPE
	SYNTAX     DisplayString
	MAX-ACCESS read-only
	STATUS     current
	DESCRIPTION
		"This shows the product version of power supply module2."
	::= { powerSupply2BasicInfo 5 }

powerSupply2InfoProductManufacturer      OBJECT-TYPE
	SYNTAX     DisplayString
	MAX-ACCESS read-only
	STATUS     current
	DESCRIPTION
		"This shows the product manufacturer of power supply module2."
	::= { powerSupply2BasicInfo 6 }

powerSupply2InfoBoardProductName         OBJECT-TYPE
	SYNTAX     DisplayString
	MAX-ACCESS read-only
	STATUS     current
	DESCRIPTION
		"Reserved."
	::= { powerSupply2BasicInfo 7 }

powerSupply2InfoBoardSerialNum           OBJECT-TYPE
	SYNTAX     DisplayString
	MAX-ACCESS read-only
	STATUS     current
	DESCRIPTION
		"Reserved."
	::= { powerSupply2BasicInfo 8 }

powerSupply2InfoBoardManufacturer        OBJECT-TYPE
	SYNTAX     DisplayString
	MAX-ACCESS read-only
	STATUS     current
	DESCRIPTION
		"Reserved."
	::= { powerSupply2BasicInfo 9 }

powerSupply2InfoSpec                     OBJECT IDENTIFIER ::= { powerSupply2BasicInfo 20 }

powerSupply2SpecRateVoltageMain          OBJECT-TYPE
	SYNTAX     Integer32
	UNITS      "0.1 V"
	MAX-ACCESS read-only
	STATUS     current
	DESCRIPTION
		"This shows the rated voltage of power supply module2.(main)"
	::= { powerSupply2InfoSpec 1 }

powerSupply2SpecRateVoltageSub           OBJECT-TYPE
	SYNTAX     Integer32
	UNITS      "0.1 V"
	MAX-ACCESS read-only
	STATUS     current
	DESCRIPTION
		"This shows the rated voltage of power supply module2.(sub)"
	::= { powerSupply2InfoSpec 2 }

powerSupply2SpecAmbientTempUpperLimit    OBJECT-TYPE
	SYNTAX     Integer32
	UNITS      "0.1 degrees C"
	MAX-ACCESS read-only
	STATUS     current
	DESCRIPTION
		"This shows the highest temperature of ambient in power supply module."
	::= { powerSupply2InfoSpec 3 }

powerSupply2SpecAmbientTempLowerLimit    OBJECT-TYPE
	SYNTAX     Integer32
	UNITS      "0.1 degrees C"
	MAX-ACCESS read-only
	STATUS     current
	DESCRIPTION
		"This shows the lowest temperature of ambient in power supply module."
	::= { powerSupply2InfoSpec 4 }

powerSupply2SpecHotSpotTempUpperLimit    OBJECT-TYPE
	SYNTAX     Integer32
	UNITS      "0.1 degrees C"
	MAX-ACCESS read-only
	STATUS     current
	DESCRIPTION
		"This shows the highest temperature of hot spot in power supply module."
	::= { powerSupply2InfoSpec 5 }

powerSupply2SpecHotSpotTempLowerLimit    OBJECT-TYPE
	SYNTAX     Integer32
	UNITS      "0.1 degrees C"
	MAX-ACCESS read-only
	STATUS     current
	DESCRIPTION
		"This shows the lowest temperature of hot spot in power supply module."
	::= { powerSupply2InfoSpec 6 }

powerSupply2SpecExhaustTempUpperLimit    OBJECT-TYPE
	SYNTAX     Integer32
	UNITS      "0.1 degrees C"
	MAX-ACCESS read-only
	STATUS     current
	DESCRIPTION
		"This shows the highest temperature of exhaust in power supply module."
	::= { powerSupply2InfoSpec 7 }

powerSupply2SpecExhaustTempLowerLimit    OBJECT-TYPE
	SYNTAX     Integer32
	UNITS      "0.1 degrees C"
	MAX-ACCESS read-only
	STATUS     current
	DESCRIPTION
		"This shows the lowest temperature of exhaust in power supply module."
	::= { powerSupply2InfoSpec 8 }

powerSupply2Capacity                     OBJECT IDENTIFIER ::= { powerSupply2 2 }

powerSupply2CapacityFan                  OBJECT-TYPE
	SYNTAX     Integer32
	MAX-ACCESS read-only
	STATUS     current
	DESCRIPTION
		"This shows the capacity fans of power supply module2."
	::= { powerSupply2Capacity 1 }

powerSupply2Settings                     OBJECT-TYPE
	SYNTAX     DisplayString
	MAX-ACCESS read-only
	STATUS     current
	DESCRIPTION
		"Reserved."
	::= { powerSupply2 3 }

powerSupply2State                        OBJECT IDENTIFIER ::= { powerSupply2 4 }

powerSupply2StateSlotNum                 OBJECT-TYPE
	SYNTAX     Integer32
	MAX-ACCESS read-only
	STATUS     current
	DESCRIPTION
		"This shows the number of installed slots of power supply module2."
	::= { powerSupply2State 1 }

powerSupply2StatePower                   OBJECT-TYPE
	SYNTAX     INTEGER {
		poweroff(1), poweron(2), unknown(3)
	}
	MAX-ACCESS read-only
	STATUS     current
	DESCRIPTION
		"This shows the power supply state of power supply module2."
	::= { powerSupply2State 2 }

powerSupply2StateHealth                  OBJECT-TYPE
	SYNTAX     INTEGER {
		normal(1), fail(2), unknown(3)
	}
	MAX-ACCESS read-only
	STATUS     current
	DESCRIPTION
		"This shows the health state of power supply module2."
	::= { powerSupply2State 3 }

powerSupply2StateAmbientTemp             OBJECT-TYPE
	SYNTAX     Integer32
	UNITS      "0.1 degrees C"
	MAX-ACCESS read-only
	STATUS     current
	DESCRIPTION
		"This shows the temperature value of ambient sensor of power supply module2."
	::= { powerSupply2State 4 }

powerSupply2StateHotSpotTemp             OBJECT-TYPE
	SYNTAX     Integer32
	UNITS      "0.1 degrees C"
	MAX-ACCESS read-only
	STATUS     current
	DESCRIPTION
		"This shows the temperature value of hot spot sensor of power supply module2."
	::= { powerSupply2State 5 }

powerSupply2StateExhaustTemp             OBJECT-TYPE
	SYNTAX     Integer32
	UNITS      "0.1 degrees C"
	MAX-ACCESS read-only
	STATUS     current
	DESCRIPTION
		"This shows the temperature value of exhaust sensor of power supply module."
	::= { powerSupply2State 6 }

powerSupply2StateMainVoltage             OBJECT-TYPE
	SYNTAX     Integer32
	UNITS      "0.1 V"
	MAX-ACCESS read-only
	STATUS     current
	DESCRIPTION
		"This shows the main voltage of power supply module2."
	::= { powerSupply2State 7 }

powerSupply2StateSubVoltage              OBJECT-TYPE
	SYNTAX     Integer32
	UNITS      "0.1 V"
	MAX-ACCESS read-only
	STATUS     current
	DESCRIPTION
		"This shows the sub voltage of power supply module2."
	::= { powerSupply2State 8 }

powerSupply2StateInputVoltage            OBJECT-TYPE
	SYNTAX     Integer32
	UNITS      "0.1 V"
	MAX-ACCESS read-only
	STATUS     current
	DESCRIPTION
		"This shows the input voltage of power supply module2."
	::= { powerSupply2State 9 }

powerSupply2StateMainCurrent             OBJECT-TYPE
	SYNTAX     Integer32
	UNITS      "0.1 A"
	MAX-ACCESS read-only
	STATUS     current
	DESCRIPTION
		"This shows the main current of power supply module2."
	::= { powerSupply2State 10 }

powerSupply2StateSubCurrent              OBJECT-TYPE
	SYNTAX     Integer32
	UNITS      "0.1 A"
	MAX-ACCESS read-only
	STATUS     current
	DESCRIPTION
		"This shows the sub current of power supply module2."
	::= { powerSupply2State 11 }

powerSupply2StateInputCurrent            OBJECT-TYPE
	SYNTAX     Integer32
	UNITS      "0.1 A"
	MAX-ACCESS read-only
	STATUS     current
	DESCRIPTION
		"This shows the input current of power supply module2."
	::= { powerSupply2State 12 }

powerSupply2StateLEDTable                OBJECT-TYPE
	SYNTAX SEQUENCE OF powerSupply2StateLEDEntry
	MAX-ACCESS not-accessible
	STATUS     current
	DESCRIPTION
		"Reserved."
	::= { powerSupply2State 13 }

powerSupply2StateLEDEntry                OBJECT-TYPE
	SYNTAX     PowerSupply2StateLEDEntry
	MAX-ACCESS not-accessible
	STATUS     current
	DESCRIPTION
		"Reserved."
	INDEX { powerSupply2StateLEDIndex }
	::= { powerSupply2StateLEDTable 1 }

PowerSupply2StateLEDEntry ::= SEQUENCE {
	powerSupply2StateLEDIndex
		Integer32,
	powerSupply2StateLEDName
		DisplayString,
	powerSupply2StateLEDType
		DisplayString,
	powerSupply2StateLEDState
		DisplayString,
	powerSupply2StateLEDColor
		DisplayString
}

powerSupply2StateLEDIndex                OBJECT-TYPE
	SYNTAX     Integer32
	MAX-ACCESS read-only
	STATUS     current
	DESCRIPTION
		"Reserved."
	::= { powerSupply2StateLEDEntry 1 }

powerSupply2StateLEDName                 OBJECT-TYPE
	SYNTAX     DisplayString
	MAX-ACCESS read-only
	STATUS     current
	DESCRIPTION
		"Reserved."
	::= { powerSupply2StateLEDEntry 2 }

powerSupply2StateLEDType                 OBJECT-TYPE
	SYNTAX     DisplayString
	MAX-ACCESS read-only
	STATUS     current
	DESCRIPTION
		"Reserved."
	::= { powerSupply2StateLEDEntry 3 }

powerSupply2StateLEDState                OBJECT-TYPE
	SYNTAX     DisplayString
	MAX-ACCESS read-only
	STATUS     current
	DESCRIPTION
		"Reserved."
	::= { powerSupply2StateLEDEntry 4 }

powerSupply2StateLEDColor                OBJECT-TYPE
	SYNTAX     DisplayString
	MAX-ACCESS read-only
	STATUS     current
	DESCRIPTION
		"Reserved."
	::= { powerSupply2StateLEDEntry 5 }

powerSupply2StateFanTable                OBJECT-TYPE
	SYNTAX SEQUENCE OF powerSupply2StateFanEntry
	MAX-ACCESS not-accessible
	STATUS     current
	DESCRIPTION
		"This shows the table of fan of power supply module2."
	::= { powerSupply2State 14 }

powerSupply2StateFanEntry                OBJECT-TYPE
	SYNTAX     PowerSupply2StateFanEntry
	MAX-ACCESS not-accessible
	STATUS     current
	DESCRIPTION
		"This shows the entry of fan of power supply module2."
	INDEX { powerSupply2StateFanIndex }
	::= { powerSupply2StateFanTable 1 }

PowerSupply2StateFanEntry ::= SEQUENCE {
	powerSupply2StateFanIndex
		Integer32,
	powerSupply2StateFanLocation
		DisplayString,
	powerSupply2StateFanRPM
		Integer32
}

powerSupply2StateFanIndex                OBJECT-TYPE
	SYNTAX     Integer32
	MAX-ACCESS read-only
	STATUS     current
	DESCRIPTION
		"This shows the index of fan of power supply module2."
	::= { powerSupply2StateFanEntry 1 }

powerSupply2StateFanLocation             OBJECT-TYPE
	SYNTAX     DisplayString
	MAX-ACCESS read-only
	STATUS     current
	DESCRIPTION
		"This shows the location of fan of power supply module2."
	::= { powerSupply2StateFanEntry 2 }

powerSupply2StateFanRPM                  OBJECT-TYPE
	SYNTAX     Integer32
	UNITS      "rpm"
	MAX-ACCESS read-only
	STATUS     current
	DESCRIPTION
		"This shows the rpm value of power supply module2."
	::= { powerSupply2StateFanEntry 3 }

powerSupply3                             OBJECT IDENTIFIER ::= { powerSupply 3 }

powerSupply3BasicInfo                    OBJECT IDENTIFIER ::= { powerSupply3 1 }

powerSupply3InfoType                     OBJECT-TYPE
	SYNTAX     DisplayString
	MAX-ACCESS read-only
	STATUS     current
	DESCRIPTION
		"Reserved."
	::= { powerSupply3BasicInfo 1 }

powerSupply3InfoProductName              OBJECT-TYPE
	SYNTAX     DisplayString
	MAX-ACCESS read-only
	STATUS     current
	DESCRIPTION
		"This shows the product name of power supply module3."
	::= { powerSupply3BasicInfo 2 }

powerSupply3InfoModel                    OBJECT-TYPE
	SYNTAX     DisplayString
	MAX-ACCESS read-only
	STATUS     current
	DESCRIPTION
		"This shows the model name of power supply module3."
	::= { powerSupply3BasicInfo 3 }

powerSupply3InfoSerialNum                OBJECT-TYPE
	SYNTAX     DisplayString
	MAX-ACCESS read-only
	STATUS     current
	DESCRIPTION
		"This shows the serial number of power supply module3."
	::= { powerSupply3BasicInfo 4 }

powerSupply3InfoProductVersion           OBJECT-TYPE
	SYNTAX     DisplayString
	MAX-ACCESS read-only
	STATUS     current
	DESCRIPTION
		"This shows the product version of power supply module3."
	::= { powerSupply3BasicInfo 5 }

powerSupply3InfoProductManufacturer      OBJECT-TYPE
	SYNTAX     DisplayString
	MAX-ACCESS read-only
	STATUS     current
	DESCRIPTION
		"This shows the product manufacturer of power supply module3."
	::= { powerSupply3BasicInfo 6 }

powerSupply3InfoBoardProductName         OBJECT-TYPE
	SYNTAX     DisplayString
	MAX-ACCESS read-only
	STATUS     current
	DESCRIPTION
		"Reserved."
	::= { powerSupply3BasicInfo 7 }

powerSupply3InfoBoardSerialNum           OBJECT-TYPE
	SYNTAX     DisplayString
	MAX-ACCESS read-only
	STATUS     current
	DESCRIPTION
		"Reserved."
	::= { powerSupply3BasicInfo 8 }

powerSupply3InfoBoardManufacturer        OBJECT-TYPE
	SYNTAX     DisplayString
	MAX-ACCESS read-only
	STATUS     current
	DESCRIPTION
		"Reserved."
	::= { powerSupply3BasicInfo 9 }

powerSupply3InfoSpec                     OBJECT IDENTIFIER ::= { powerSupply3BasicInfo 20 }

powerSupply3SpecRateVoltageMain          OBJECT-TYPE
	SYNTAX     Integer32
	UNITS      "0.1 V"
	MAX-ACCESS read-only
	STATUS     current
	DESCRIPTION
		"This shows the rated voltage of power supply module3.(main)"
	::= { powerSupply3InfoSpec 1 }

powerSupply3SpecRateVoltageSub           OBJECT-TYPE
	SYNTAX     Integer32
	UNITS      "0.1 V"
	MAX-ACCESS read-only
	STATUS     current
	DESCRIPTION
		"This shows the rated voltage of power supply module3.(sub)"
	::= { powerSupply3InfoSpec 2 }

powerSupply3SpecAmbientTempUpperLimit    OBJECT-TYPE
	SYNTAX     Integer32
	UNITS      "0.1 degrees C"
	MAX-ACCESS read-only
	STATUS     current
	DESCRIPTION
		"This shows the highest temperature of ambient in power supply module."
	::= { powerSupply3InfoSpec 3 }

powerSupply3SpecAmbientTempLowerLimit    OBJECT-TYPE
	SYNTAX     Integer32
	UNITS      "0.1 degrees C"
	MAX-ACCESS read-only
	STATUS     current
	DESCRIPTION
		"This shows the lowest temperature of ambient in power supply module."
	::= { powerSupply3InfoSpec 4 }

powerSupply3SpecHotSpotTempUpperLimit    OBJECT-TYPE
	SYNTAX     Integer32
	UNITS      "0.1 degrees C"
	MAX-ACCESS read-only
	STATUS     current
	DESCRIPTION
		"This shows the highest temperature of hot spot in power supply module."
	::= { powerSupply3InfoSpec 5 }

powerSupply3SpecHotSpotTempLowerLimit    OBJECT-TYPE
	SYNTAX     Integer32
	UNITS      "0.1 degrees C"
	MAX-ACCESS read-only
	STATUS     current
	DESCRIPTION
		"This shows the lowest temperature of hot spot in power supply module."
	::= { powerSupply3InfoSpec 6 }

powerSupply3SpecExhaustTempUpperLimit    OBJECT-TYPE
	SYNTAX     Integer32
	UNITS      "0.1 degrees C"
	MAX-ACCESS read-only
	STATUS     current
	DESCRIPTION
		"This shows the highest temperature of exhaust in power supply module."
	::= { powerSupply3InfoSpec 7 }

powerSupply3SpecExhaustTempLowerLimit    OBJECT-TYPE
	SYNTAX     Integer32
	UNITS      "0.1 degrees C"
	MAX-ACCESS read-only
	STATUS     current
	DESCRIPTION
		"This shows the lowest temperature of exhaust in power supply module."
	::= { powerSupply3InfoSpec 8 }

powerSupply3Capacity                     OBJECT IDENTIFIER ::= { powerSupply3 2 }

powerSupply3CapacityFan                  OBJECT-TYPE
	SYNTAX     Integer32
	MAX-ACCESS read-only
	STATUS     current
	DESCRIPTION
		"This shows the capacity fans of power supply module3."
	::= { powerSupply3Capacity 1 }

powerSupply3Settings                     OBJECT-TYPE
	SYNTAX     DisplayString
	MAX-ACCESS read-only
	STATUS     current
	DESCRIPTION
		"Reserved."
	::= { powerSupply3 3 }

powerSupply3State                        OBJECT IDENTIFIER ::= { powerSupply3 4 }

powerSupply3StateSlotNum                 OBJECT-TYPE
	SYNTAX     Integer32
	MAX-ACCESS read-only
	STATUS     current
	DESCRIPTION
		"This shows the number of installed slots of power supply module3."
	::= { powerSupply3State 1 }

powerSupply3StatePower                   OBJECT-TYPE
	SYNTAX     INTEGER {
		poweroff(1), poweron(2), unknown(3)
	}
	MAX-ACCESS read-only
	STATUS     current
	DESCRIPTION
		"This shows the power supply state of power supply module3."
	::= { powerSupply3State 2 }

powerSupply3StateHealth                  OBJECT-TYPE
	SYNTAX     INTEGER {
		normal(1), fail(2), unknown(3)
	}
	MAX-ACCESS read-only
	STATUS     current
	DESCRIPTION
		"This shows the health state of power supply module3."
	::= { powerSupply3State 3 }

powerSupply3StateAmbientTemp             OBJECT-TYPE
	SYNTAX     Integer32
	UNITS      "0.1 degrees C"
	MAX-ACCESS read-only
	STATUS     current
	DESCRIPTION
		"This shows the temperature value of ambient sensor of power supply module3."
	::= { powerSupply3State 4 }

powerSupply3StateHotSpotTemp             OBJECT-TYPE
	SYNTAX     Integer32
	UNITS      "0.1 degrees C"
	MAX-ACCESS read-only
	STATUS     current
	DESCRIPTION
		"This shows the temperature value of hot spot sensor of power supply module3."
	::= { powerSupply3State 5 }

powerSupply3StateExhaustTemp             OBJECT-TYPE
	SYNTAX     Integer32
	UNITS      "0.1 degrees C"
	MAX-ACCESS read-only
	STATUS     current
	DESCRIPTION
		"This shows the temperature value of exhaust sensor of power supply module."
	::= { powerSupply3State 6 }

powerSupply3StateMainVoltage             OBJECT-TYPE
	SYNTAX     Integer32
	UNITS      "0.1 V"
	MAX-ACCESS read-only
	STATUS     current
	DESCRIPTION
		"This shows the main voltage of power supply module3."
	::= { powerSupply3State 7 }

powerSupply3StateSubVoltage              OBJECT-TYPE
	SYNTAX     Integer32
	UNITS      "0.1 V"
	MAX-ACCESS read-only
	STATUS     current
	DESCRIPTION
		"This shows the sub voltage of power supply module3."
	::= { powerSupply3State 8 }

powerSupply3StateInputVoltage            OBJECT-TYPE
	SYNTAX     Integer32
	UNITS      "0.1 V"
	MAX-ACCESS read-only
	STATUS     current
	DESCRIPTION
		"This shows the input voltage of power supply module3."
	::= { powerSupply3State 9 }

powerSupply3StateMainCurrent             OBJECT-TYPE
	SYNTAX     Integer32
	UNITS      "0.1 A"
	MAX-ACCESS read-only
	STATUS     current
	DESCRIPTION
		"This shows the main current of power supply module3."
	::= { powerSupply3State 10 }

powerSupply3StateSubCurrent              OBJECT-TYPE
	SYNTAX     Integer32
	UNITS      "0.1 A"
	MAX-ACCESS read-only
	STATUS     current
	DESCRIPTION
		"This shows the sub current of power supply module3."
	::= { powerSupply3State 11 }

powerSupply3StateInputCurrent            OBJECT-TYPE
	SYNTAX     Integer32
	UNITS      "0.1 A"
	MAX-ACCESS read-only
	STATUS     current
	DESCRIPTION
		"This shows the input current of power supply module3."
	::= { powerSupply3State 12 }

powerSupply3StateLEDTable                OBJECT-TYPE
	SYNTAX SEQUENCE OF powerSupply3StateLEDEntry
	MAX-ACCESS not-accessible
	STATUS     current
	DESCRIPTION
		"Reserved."
	::= { powerSupply3State 13 }

powerSupply3StateLEDEntry                OBJECT-TYPE
	SYNTAX     PowerSupply3StateLEDEntry
	MAX-ACCESS not-accessible
	STATUS     current
	DESCRIPTION
		"Reserved."
	INDEX { powerSupply3StateLEDIndex }
	::= { powerSupply3StateLEDTable 1 }

PowerSupply3StateLEDEntry ::= SEQUENCE {
	powerSupply3StateLEDIndex
		Integer32,
	powerSupply3StateLEDName
		DisplayString,
	powerSupply3StateLEDType
		DisplayString,
	powerSupply3StateLEDState
		DisplayString,
	powerSupply3StateLEDColor
		DisplayString
}

powerSupply3StateLEDIndex                OBJECT-TYPE
	SYNTAX     Integer32
	MAX-ACCESS read-only
	STATUS     current
	DESCRIPTION
		"Reserved."
	::= { powerSupply3StateLEDEntry 1 }

powerSupply3StateLEDName                 OBJECT-TYPE
	SYNTAX     DisplayString
	MAX-ACCESS read-only
	STATUS     current
	DESCRIPTION
		"Reserved."
	::= { powerSupply3StateLEDEntry 2 }

powerSupply3StateLEDType                 OBJECT-TYPE
	SYNTAX     DisplayString
	MAX-ACCESS read-only
	STATUS     current
	DESCRIPTION
		"Reserved."
	::= { powerSupply3StateLEDEntry 3 }

powerSupply3StateLEDState                OBJECT-TYPE
	SYNTAX     DisplayString
	MAX-ACCESS read-only
	STATUS     current
	DESCRIPTION
		"Reserved."
	::= { powerSupply3StateLEDEntry 4 }

powerSupply3StateLEDColor                OBJECT-TYPE
	SYNTAX     DisplayString
	MAX-ACCESS read-only
	STATUS     current
	DESCRIPTION
		"Reserved."
	::= { powerSupply3StateLEDEntry 5 }

powerSupply3StateFanTable                OBJECT-TYPE
	SYNTAX SEQUENCE OF powerSupply3StateFanEntry
	MAX-ACCESS not-accessible
	STATUS     current
	DESCRIPTION
		"This shows the table of fan of power supply module3."
	::= { powerSupply3State 14 }

powerSupply3StateFanEntry                OBJECT-TYPE
	SYNTAX     PowerSupply3StateFanEntry
	MAX-ACCESS not-accessible
	STATUS     current
	DESCRIPTION
		"This shows the entry of fan of power supply module3."
	INDEX { powerSupply3StateFanIndex }
	::= { powerSupply3StateFanTable 1 }

PowerSupply3StateFanEntry ::= SEQUENCE {
	powerSupply3StateFanIndex
		Integer32,
	powerSupply3StateFanLocation
		DisplayString,
	powerSupply3StateFanRPM
		Integer32
}

powerSupply3StateFanIndex                OBJECT-TYPE
	SYNTAX     Integer32
	MAX-ACCESS read-only
	STATUS     current
	DESCRIPTION
		"This shows the index of fan of power supply module3."
	::= { powerSupply3StateFanEntry 1 }

powerSupply3StateFanLocation             OBJECT-TYPE
	SYNTAX     DisplayString
	MAX-ACCESS read-only
	STATUS     current
	DESCRIPTION
		"This shows the location of fan of power supply module3."
	::= { powerSupply3StateFanEntry 2 }

powerSupply3StateFanRPM                  OBJECT-TYPE
	SYNTAX     Integer32
	UNITS      "rpm"
	MAX-ACCESS read-only
	STATUS     current
	DESCRIPTION
		"This shows the rpm value of power supply module3."
	::= { powerSupply3StateFanEntry 3 }

powerSupply4                             OBJECT IDENTIFIER ::= { powerSupply 4 }

powerSupply4BasicInfo                    OBJECT IDENTIFIER ::= { powerSupply4 1 }

powerSupply4InfoType                     OBJECT-TYPE
	SYNTAX     DisplayString
	MAX-ACCESS read-only
	STATUS     current
	DESCRIPTION
		"Reserved."
	::= { powerSupply4BasicInfo 1 }

powerSupply4InfoProductName              OBJECT-TYPE
	SYNTAX     DisplayString
	MAX-ACCESS read-only
	STATUS     current
	DESCRIPTION
		"This shows the product name of power supply module3."
	::= { powerSupply4BasicInfo 2 }

powerSupply4InfoModel                    OBJECT-TYPE
	SYNTAX     DisplayString
	MAX-ACCESS read-only
	STATUS     current
	DESCRIPTION
		"This shows the model name of power supply module3."
	::= { powerSupply4BasicInfo 3 }

powerSupply4InfoSerialNum                OBJECT-TYPE
	SYNTAX     DisplayString
	MAX-ACCESS read-only
	STATUS     current
	DESCRIPTION
		"This shows the serial number of power supply module3."
	::= { powerSupply4BasicInfo 4 }

powerSupply4InfoProductVersion           OBJECT-TYPE
	SYNTAX     DisplayString
	MAX-ACCESS read-only
	STATUS     current
	DESCRIPTION
		"This shows the product version of power supply module3."
	::= { powerSupply4BasicInfo 5 }

powerSupply4InfoProductManufacturer      OBJECT-TYPE
	SYNTAX     DisplayString
	MAX-ACCESS read-only
	STATUS     current
	DESCRIPTION
		"This shows the product manufacturer of power supply module3."
	::= { powerSupply4BasicInfo 6 }

powerSupply4InfoBoardProductName         OBJECT-TYPE
	SYNTAX     DisplayString
	MAX-ACCESS read-only
	STATUS     current
	DESCRIPTION
		"Reserved."
	::= { powerSupply4BasicInfo 7 }

powerSupply4InfoBoardSerialNum           OBJECT-TYPE
	SYNTAX     DisplayString
	MAX-ACCESS read-only
	STATUS     current
	DESCRIPTION
		"Reserved."
	::= { powerSupply4BasicInfo 8 }

powerSupply4InfoBoardManufacturer        OBJECT-TYPE
	SYNTAX     DisplayString
	MAX-ACCESS read-only
	STATUS     current
	DESCRIPTION
		"Reserved."
	::= { powerSupply4BasicInfo 9 }

powerSupply4InfoSpec                     OBJECT IDENTIFIER ::= { powerSupply4BasicInfo 20 }

powerSupply4SpecRateVoltageMain          OBJECT-TYPE
	SYNTAX     Integer32
	UNITS      "0.1 V"
	MAX-ACCESS read-only
	STATUS     current
	DESCRIPTION
		"This shows the rated voltage of power supply module3.(main)"
	::= { powerSupply4InfoSpec 1 }

powerSupply4SpecRateVoltageSub           OBJECT-TYPE
	SYNTAX     Integer32
	UNITS      "0.1 V"
	MAX-ACCESS read-only
	STATUS     current
	DESCRIPTION
		"This shows the rated voltage of power supply module3.(sub)"
	::= { powerSupply4InfoSpec 2 }

powerSupply4SpecAmbientTempUpperLimit    OBJECT-TYPE
	SYNTAX     Integer32
	UNITS      "0.1 degrees C"
	MAX-ACCESS read-only
	STATUS     current
	DESCRIPTION
		"This shows the highest temperature of ambient in power supply module."
	::= { powerSupply4InfoSpec 3 }

powerSupply4SpecAmbientTempLowerLimit    OBJECT-TYPE
	SYNTAX     Integer32
	UNITS      "0.1 degrees C"
	MAX-ACCESS read-only
	STATUS     current
	DESCRIPTION
		"This shows the lowest temperature of ambient in power supply module."
	::= { powerSupply4InfoSpec 4 }

powerSupply4SpecHotSpotTempUpperLimit    OBJECT-TYPE
	SYNTAX     Integer32
	UNITS      "0.1 degrees C"
	MAX-ACCESS read-only
	STATUS     current
	DESCRIPTION
		"This shows the highest temperature of hot spot in power supply module."
	::= { powerSupply4InfoSpec 5 }

powerSupply4SpecHotSpotTempLowerLimit    OBJECT-TYPE
	SYNTAX     Integer32
	UNITS      "0.1 degrees C"
	MAX-ACCESS read-only
	STATUS     current
	DESCRIPTION
		"This shows the lowest temperature of hot spot in power supply module."
	::= { powerSupply4InfoSpec 6 }

powerSupply4SpecExhaustTempUpperLimit    OBJECT-TYPE
	SYNTAX     Integer32
	UNITS      "0.1 degrees C"
	MAX-ACCESS read-only
	STATUS     current
	DESCRIPTION
		"This shows the highest temperature of exhaust in power supply module."
	::= { powerSupply4InfoSpec 7 }

powerSupply4SpecExhaustTempLowerLimit    OBJECT-TYPE
	SYNTAX     Integer32
	UNITS      "0.1 degrees C"
	MAX-ACCESS read-only
	STATUS     current
	DESCRIPTION
		"This shows the lowest temperature of exhaust in power supply module."
	::= { powerSupply4InfoSpec 8 }

powerSupply4Capacity                     OBJECT IDENTIFIER ::= { powerSupply4 2 }

powerSupply4CapacityFan                  OBJECT-TYPE
	SYNTAX     Integer32
	MAX-ACCESS read-only
	STATUS     current
	DESCRIPTION
		"This shows the capacity fans of power supply module3."
	::= { powerSupply4Capacity 1 }

powerSupply4Settings                     OBJECT-TYPE
	SYNTAX     DisplayString
	MAX-ACCESS read-only
	STATUS     current
	DESCRIPTION
		"Reserved."
	::= { powerSupply4 3 }

powerSupply4State                        OBJECT IDENTIFIER ::= { powerSupply4 4 }

powerSupply4StateSlotNum                 OBJECT-TYPE
	SYNTAX     Integer32
	MAX-ACCESS read-only
	STATUS     current
	DESCRIPTION
		"This shows the number of installed slots of power supply module3."
	::= { powerSupply4State 1 }

powerSupply4StatePower                   OBJECT-TYPE
	SYNTAX     INTEGER {
		poweroff(1), poweron(2), unknown(3)
	}
	MAX-ACCESS read-only
	STATUS     current
	DESCRIPTION
		"This shows the power supply state of power supply module3."
	::= { powerSupply4State 2 }

powerSupply4StateHealth                  OBJECT-TYPE
	SYNTAX     INTEGER {
		normal(1), fail(2), unknown(3)
	}
	MAX-ACCESS read-only
	STATUS     current
	DESCRIPTION
		"This shows the health state of power supply module3."
	::= { powerSupply4State 3 }

powerSupply4StateAmbientTemp             OBJECT-TYPE
	SYNTAX     Integer32
	UNITS      "0.1 degrees C"
	MAX-ACCESS read-only
	STATUS     current
	DESCRIPTION
		"This shows the temperature value of ambient sensor of power supply module3."
	::= { powerSupply4State 4 }

powerSupply4StateHotSpotTemp             OBJECT-TYPE
	SYNTAX     Integer32
	UNITS      "0.1 degrees C"
	MAX-ACCESS read-only
	STATUS     current
	DESCRIPTION
		"This shows the temperature value of hot spot sensor of power supply module3."
	::= { powerSupply4State 5 }

powerSupply4StateExhaustTemp             OBJECT-TYPE
	SYNTAX     Integer32
	UNITS      "0.1 degrees C"
	MAX-ACCESS read-only
	STATUS     current
	DESCRIPTION
		"This shows the temperature value of exhaust sensor of power supply module."
	::= { powerSupply4State 6 }

powerSupply4StateMainVoltage             OBJECT-TYPE
	SYNTAX     Integer32
	UNITS      "0.1 V"
	MAX-ACCESS read-only
	STATUS     current
	DESCRIPTION
		"This shows the main voltage of power supply module3."
	::= { powerSupply4State 7 }

powerSupply4StateSubVoltage              OBJECT-TYPE
	SYNTAX     Integer32
	UNITS      "0.1 V"
	MAX-ACCESS read-only
	STATUS     current
	DESCRIPTION
		"This shows the sub voltage of power supply module3."
	::= { powerSupply4State 8 }

powerSupply4StateInputVoltage            OBJECT-TYPE
	SYNTAX     Integer32
	UNITS      "0.1 V"
	MAX-ACCESS read-only
	STATUS     current
	DESCRIPTION
		"This shows the input voltage of power supply module3."
	::= { powerSupply4State 9 }

powerSupply4StateMainCurrent             OBJECT-TYPE
	SYNTAX     Integer32
	UNITS      "0.1 A"
	MAX-ACCESS read-only
	STATUS     current
	DESCRIPTION
		"This shows the main current of power supply module3."
	::= { powerSupply4State 10 }

powerSupply4StateSubCurrent              OBJECT-TYPE
	SYNTAX     Integer32
	UNITS      "0.1 A"
	MAX-ACCESS read-only
	STATUS     current
	DESCRIPTION
		"This shows the sub current of power supply module3."
	::= { powerSupply4State 11 }

powerSupply4StateInputCurrent            OBJECT-TYPE
	SYNTAX     Integer32
	UNITS      "0.1 A"
	MAX-ACCESS read-only
	STATUS     current
	DESCRIPTION
		"This shows the input current of power supply module3."
	::= { powerSupply4State 12 }

powerSupply4StateLEDTable                OBJECT-TYPE
	SYNTAX SEQUENCE OF powerSupply4StateLEDEntry
	MAX-ACCESS not-accessible
	STATUS     current
	DESCRIPTION
		"Reserved."
	::= { powerSupply4State 13 }

powerSupply4StateLEDEntry                OBJECT-TYPE
	SYNTAX     PowerSupply4StateLEDEntry
	MAX-ACCESS not-accessible
	STATUS     current
	DESCRIPTION
		"Reserved."
	INDEX { powerSupply4StateLEDIndex }
	::= { powerSupply4StateLEDTable 1 }

PowerSupply4StateLEDEntry ::= SEQUENCE {
	powerSupply4StateLEDIndex
		Integer32,
	powerSupply4StateLEDName
		DisplayString,
	powerSupply4StateLEDType
		DisplayString,
	powerSupply4StateLEDState
		DisplayString,
	powerSupply4StateLEDColor
		DisplayString
}

powerSupply4StateLEDIndex                OBJECT-TYPE
	SYNTAX     Integer32
	MAX-ACCESS read-only
	STATUS     current
	DESCRIPTION
		"Reserved."
	::= { powerSupply4StateLEDEntry 1 }

powerSupply4StateLEDName                 OBJECT-TYPE
	SYNTAX     DisplayString
	MAX-ACCESS read-only
	STATUS     current
	DESCRIPTION
		"Reserved."
	::= { powerSupply4StateLEDEntry 2 }

powerSupply4StateLEDType                 OBJECT-TYPE
	SYNTAX     DisplayString
	MAX-ACCESS read-only
	STATUS     current
	DESCRIPTION
		"Reserved."
	::= { powerSupply4StateLEDEntry 3 }

powerSupply4StateLEDState                OBJECT-TYPE
	SYNTAX     DisplayString
	MAX-ACCESS read-only
	STATUS     current
	DESCRIPTION
		"Reserved."
	::= { powerSupply4StateLEDEntry 4 }

powerSupply4StateLEDColor                OBJECT-TYPE
	SYNTAX     DisplayString
	MAX-ACCESS read-only
	STATUS     current
	DESCRIPTION
		"Reserved."
	::= { powerSupply4StateLEDEntry 5 }

powerSupply4StateFanTable                OBJECT-TYPE
	SYNTAX SEQUENCE OF powerSupply4StateFanEntry
	MAX-ACCESS not-accessible
	STATUS     current
	DESCRIPTION
		"This shows the table of fan of power supply module3."
	::= { powerSupply4State 14 }

powerSupply4StateFanEntry                OBJECT-TYPE
	SYNTAX     PowerSupply4StateFanEntry
	MAX-ACCESS not-accessible
	STATUS     current
	DESCRIPTION
		"This shows the entry of fan of power supply module3."
	INDEX { powerSupply4StateFanIndex }
	::= { powerSupply4StateFanTable 1 }

PowerSupply4StateFanEntry ::= SEQUENCE {
	powerSupply4StateFanIndex
		Integer32,
	powerSupply4StateFanLocation
		DisplayString,
	powerSupply4StateFanRPM
		Integer32
}

powerSupply4StateFanIndex                OBJECT-TYPE
	SYNTAX     Integer32
	MAX-ACCESS read-only
	STATUS     current
	DESCRIPTION
		"This shows the index of fan of power supply module3."
	::= { powerSupply4StateFanEntry 1 }

powerSupply4StateFanLocation             OBJECT-TYPE
	SYNTAX     DisplayString
	MAX-ACCESS read-only
	STATUS     current
	DESCRIPTION
		"This shows the location of fan of power supply module3."
	::= { powerSupply4StateFanEntry 2 }

powerSupply4StateFanRPM                  OBJECT-TYPE
	SYNTAX     Integer32
	UNITS      "rpm"
	MAX-ACCESS read-only
	STATUS     current
	DESCRIPTION
		"This shows the rpm value of power supply module3."
	::= { powerSupply4StateFanEntry 3 }

powerSupply5                             OBJECT IDENTIFIER ::= { powerSupply 5 }

powerSupply5BasicInfo                    OBJECT IDENTIFIER ::= { powerSupply5 1 }

powerSupply5InfoType                     OBJECT-TYPE
	SYNTAX     DisplayString
	MAX-ACCESS read-only
	STATUS     current
	DESCRIPTION
		"Reserved."
	::= { powerSupply5BasicInfo 1 }

powerSupply5InfoProductName              OBJECT-TYPE
	SYNTAX     DisplayString
	MAX-ACCESS read-only
	STATUS     current
	DESCRIPTION
		"This shows the product name of power supply module5."
	::= { powerSupply5BasicInfo 2 }

powerSupply5InfoModel                    OBJECT-TYPE
	SYNTAX     DisplayString
	MAX-ACCESS read-only
	STATUS     current
	DESCRIPTION
		"This shows the model name of power supply module5."
	::= { powerSupply5BasicInfo 3 }

powerSupply5InfoSerialNum                OBJECT-TYPE
	SYNTAX     DisplayString
	MAX-ACCESS read-only
	STATUS     current
	DESCRIPTION
		"This shows the serial number of power supply module5."
	::= { powerSupply5BasicInfo 4 }

powerSupply5InfoProductVersion           OBJECT-TYPE
	SYNTAX     DisplayString
	MAX-ACCESS read-only
	STATUS     current
	DESCRIPTION
		"This shows the product version of power supply module5."
	::= { powerSupply5BasicInfo 5 }

powerSupply5InfoProductManufacturer      OBJECT-TYPE
	SYNTAX     DisplayString
	MAX-ACCESS read-only
	STATUS     current
	DESCRIPTION
		"This shows the product manufacturer of power supply module5."
	::= { powerSupply5BasicInfo 6 }

powerSupply5InfoBoardProductName         OBJECT-TYPE
	SYNTAX     DisplayString
	MAX-ACCESS read-only
	STATUS     current
	DESCRIPTION
		"Reserved."
	::= { powerSupply5BasicInfo 7 }

powerSupply5InfoBoardSerialNum           OBJECT-TYPE
	SYNTAX     DisplayString
	MAX-ACCESS read-only
	STATUS     current
	DESCRIPTION
		"Reserved."
	::= { powerSupply5BasicInfo 8 }

powerSupply5InfoBoardManufacturer        OBJECT-TYPE
	SYNTAX     DisplayString
	MAX-ACCESS read-only
	STATUS     current
	DESCRIPTION
		"Reserved."
	::= { powerSupply5BasicInfo 9 }

powerSupply5InfoSpec                     OBJECT IDENTIFIER ::= { powerSupply5BasicInfo 20 }

powerSupply5SpecRateVoltageMain          OBJECT-TYPE
	SYNTAX     Integer32
	UNITS      "0.1 V"
	MAX-ACCESS read-only
	STATUS     current
	DESCRIPTION
		"This shows the rated voltage of power supply module5.(main)"
	::= { powerSupply5InfoSpec 1 }

powerSupply5SpecRateVoltageSub           OBJECT-TYPE
	SYNTAX     Integer32
	UNITS      "0.1 V"
	MAX-ACCESS read-only
	STATUS     current
	DESCRIPTION
		"This shows the rated voltage of power supply module5.(sub)"
	::= { powerSupply5InfoSpec 2 }

powerSupply5SpecAmbientTempUpperLimit    OBJECT-TYPE
	SYNTAX     Integer32
	UNITS      "0.1 degrees C"
	MAX-ACCESS read-only
	STATUS     current
	DESCRIPTION
		"This shows the highest temperature of ambient in power supply module."
	::= { powerSupply5InfoSpec 3 }

powerSupply5SpecAmbientTempLowerLimit    OBJECT-TYPE
	SYNTAX     Integer32
	UNITS      "0.1 degrees C"
	MAX-ACCESS read-only
	STATUS     current
	DESCRIPTION
		"This shows the lowest temperature of ambient in power supply module."
	::= { powerSupply5InfoSpec 4 }

powerSupply5SpecHotSpotTempUpperLimit    OBJECT-TYPE
	SYNTAX     Integer32
	UNITS      "0.1 degrees C"
	MAX-ACCESS read-only
	STATUS     current
	DESCRIPTION
		"This shows the highest temperature of hot spot in power supply module."
	::= { powerSupply5InfoSpec 5 }

powerSupply5SpecHotSpotTempLowerLimit    OBJECT-TYPE
	SYNTAX     Integer32
	UNITS      "0.1 degrees C"
	MAX-ACCESS read-only
	STATUS     current
	DESCRIPTION
		"This shows the lowest temperature of hot spot in power supply module."
	::= { powerSupply5InfoSpec 6 }

powerSupply5SpecExhaustTempUpperLimit    OBJECT-TYPE
	SYNTAX     Integer32
	UNITS      "0.1 degrees C"
	MAX-ACCESS read-only
	STATUS     current
	DESCRIPTION
		"This shows the highest temperature of exhaust in power supply module."
	::= { powerSupply5InfoSpec 7 }

powerSupply5SpecExhaustTempLowerLimit    OBJECT-TYPE
	SYNTAX     Integer32
	UNITS      "0.1 degrees C"
	MAX-ACCESS read-only
	STATUS     current
	DESCRIPTION
		"This shows the lowest temperature of exhaust in power supply module."
	::= { powerSupply5InfoSpec 8 }

powerSupply5Capacity                     OBJECT IDENTIFIER ::= { powerSupply5 2 }

powerSupply5CapacityFan                  OBJECT-TYPE
	SYNTAX     Integer32
	MAX-ACCESS read-only
	STATUS     current
	DESCRIPTION
		"This shows the capacity fans of power supply module5."
	::= { powerSupply5Capacity 1 }

powerSupply5Settings                     OBJECT-TYPE
	SYNTAX     DisplayString
	MAX-ACCESS read-only
	STATUS     current
	DESCRIPTION
		"Reserved."
	::= { powerSupply5 3 }

powerSupply5State                        OBJECT IDENTIFIER ::= { powerSupply5 4 }

powerSupply5StateSlotNum                 OBJECT-TYPE
	SYNTAX     Integer32
	MAX-ACCESS read-only
	STATUS     current
	DESCRIPTION
		"This shows the number of installed slots of power supply module5."
	::= { powerSupply5State 1 }

powerSupply5StatePower                   OBJECT-TYPE
	SYNTAX     INTEGER {
		poweroff(1), poweron(2), unknown(3)
	}
	MAX-ACCESS read-only
	STATUS     current
	DESCRIPTION
		"This shows the power supply state of power supply module5."
	::= { powerSupply5State 2 }

powerSupply5StateHealth                  OBJECT-TYPE
	SYNTAX     INTEGER {
		normal(1), fail(2), unknown(3)
	}
	MAX-ACCESS read-only
	STATUS     current
	DESCRIPTION
		"This shows the health state of power supply module5."
	::= { powerSupply5State 3 }

powerSupply5StateAmbientTemp             OBJECT-TYPE
	SYNTAX     Integer32
	UNITS      "0.1 degrees C"
	MAX-ACCESS read-only
	STATUS     current
	DESCRIPTION
		"This shows the temperature value of ambient sensor of power supply module5."
	::= { powerSupply5State 4 }

powerSupply5StateHotSpotTemp             OBJECT-TYPE
	SYNTAX     Integer32
	UNITS      "0.1 degrees C"
	MAX-ACCESS read-only
	STATUS     current
	DESCRIPTION
		"This shows the temperature value of hot spot sensor of power supply module5."
	::= { powerSupply5State 5 }

powerSupply5StateExhaustTemp             OBJECT-TYPE
	SYNTAX     Integer32
	UNITS      "0.1 degrees C"
	MAX-ACCESS read-only
	STATUS     current
	DESCRIPTION
		"This shows the temperature value of exhaust sensor of power supply module."
	::= { powerSupply5State 6 }

powerSupply5StateMainVoltage             OBJECT-TYPE
	SYNTAX     Integer32
	UNITS      "0.1 V"
	MAX-ACCESS read-only
	STATUS     current
	DESCRIPTION
		"This shows the main voltage of power supply module5."
	::= { powerSupply5State 7 }

powerSupply5StateSubVoltage              OBJECT-TYPE
	SYNTAX     Integer32
	UNITS      "0.1 V"
	MAX-ACCESS read-only
	STATUS     current
	DESCRIPTION
		"This shows the sub voltage of power supply module5."
	::= { powerSupply5State 8 }

powerSupply5StateInputVoltage            OBJECT-TYPE
	SYNTAX     Integer32
	UNITS      "0.1 V"
	MAX-ACCESS read-only
	STATUS     current
	DESCRIPTION
		"This shows the input voltage of power supply module5."
	::= { powerSupply5State 9 }

powerSupply5StateMainCurrent             OBJECT-TYPE
	SYNTAX     Integer32
	UNITS      "0.1 A"
	MAX-ACCESS read-only
	STATUS     current
	DESCRIPTION
		"This shows the main current of power supply module5."
	::= { powerSupply5State 10 }

powerSupply5StateSubCurrent              OBJECT-TYPE
	SYNTAX     Integer32
	UNITS      "0.1 A"
	MAX-ACCESS read-only
	STATUS     current
	DESCRIPTION
		"This shows the sub current of power supply module5."
	::= { powerSupply5State 11 }

powerSupply5StateInputCurrent            OBJECT-TYPE
	SYNTAX     Integer32
	UNITS      "0.1 A"
	MAX-ACCESS read-only
	STATUS     current
	DESCRIPTION
		"This shows the input current of power supply module5."
	::= { powerSupply5State 12 }

powerSupply5StateLEDTable                OBJECT-TYPE
	SYNTAX SEQUENCE OF powerSupply5StateLEDEntry
	MAX-ACCESS not-accessible
	STATUS     current
	DESCRIPTION
		"Reserved."
	::= { powerSupply5State 13 }

powerSupply5StateLEDEntry                OBJECT-TYPE
	SYNTAX     PowerSupply5StateLEDEntry
	MAX-ACCESS not-accessible
	STATUS     current
	DESCRIPTION
		"Reserved."
	INDEX { powerSupply5StateLEDIndex }
	::= { powerSupply5StateLEDTable 1 }

PowerSupply5StateLEDEntry ::= SEQUENCE {
	powerSupply5StateLEDIndex
		Integer32,
	powerSupply5StateLEDName
		DisplayString,
	powerSupply5StateLEDType
		DisplayString,
	powerSupply5StateLEDState
		DisplayString,
	powerSupply5StateLEDColor
		DisplayString
}

powerSupply5StateLEDIndex                OBJECT-TYPE
	SYNTAX     Integer32
	MAX-ACCESS read-only
	STATUS     current
	DESCRIPTION
		"Reserved."
	::= { powerSupply5StateLEDEntry 1 }

powerSupply5StateLEDName                 OBJECT-TYPE
	SYNTAX     DisplayString
	MAX-ACCESS read-only
	STATUS     current
	DESCRIPTION
		"Reserved."
	::= { powerSupply5StateLEDEntry 2 }

powerSupply5StateLEDType                 OBJECT-TYPE
	SYNTAX     DisplayString
	MAX-ACCESS read-only
	STATUS     current
	DESCRIPTION
		"Reserved."
	::= { powerSupply5StateLEDEntry 3 }

powerSupply5StateLEDState                OBJECT-TYPE
	SYNTAX     DisplayString
	MAX-ACCESS read-only
	STATUS     current
	DESCRIPTION
		"Reserved."
	::= { powerSupply5StateLEDEntry 4 }

powerSupply5StateLEDColor                OBJECT-TYPE
	SYNTAX     DisplayString
	MAX-ACCESS read-only
	STATUS     current
	DESCRIPTION
		"Reserved."
	::= { powerSupply5StateLEDEntry 5 }

powerSupply5StateFanTable                OBJECT-TYPE
	SYNTAX SEQUENCE OF powerSupply5StateFanEntry
	MAX-ACCESS not-accessible
	STATUS     current
	DESCRIPTION
		"This shows the table of fan of power supply module5."
	::= { powerSupply5State 14 }

powerSupply5StateFanEntry                OBJECT-TYPE
	SYNTAX     PowerSupply5StateFanEntry
	MAX-ACCESS not-accessible
	STATUS     current
	DESCRIPTION
		"This shows the entry of fan of power supply module5."
	INDEX { powerSupply5StateFanIndex }
	::= { powerSupply5StateFanTable 1 }

PowerSupply5StateFanEntry ::= SEQUENCE {
	powerSupply5StateFanIndex
		Integer32,
	powerSupply5StateFanLocation
		DisplayString,
	powerSupply5StateFanRPM
		Integer32
}

powerSupply5StateFanIndex                OBJECT-TYPE
	SYNTAX     Integer32
	MAX-ACCESS read-only
	STATUS     current
	DESCRIPTION
		"This shows the index of fan of power supply module5."
	::= { powerSupply5StateFanEntry 1 }

powerSupply5StateFanLocation             OBJECT-TYPE
	SYNTAX     DisplayString
	MAX-ACCESS read-only
	STATUS     current
	DESCRIPTION
		"This shows the location of fan of power supply module5."
	::= { powerSupply5StateFanEntry 2 }

powerSupply5StateFanRPM                  OBJECT-TYPE
	SYNTAX     Integer32
	UNITS      "rpm"
	MAX-ACCESS read-only
	STATUS     current
	DESCRIPTION
		"This shows the rpm value of power supply module5."
	::= { powerSupply5StateFanEntry 3 }

powerSupply6                             OBJECT IDENTIFIER ::= { powerSupply 6 }

powerSupply6BasicInfo                    OBJECT IDENTIFIER ::= { powerSupply6 1 }

powerSupply6InfoType                     OBJECT-TYPE
	SYNTAX     DisplayString
	MAX-ACCESS read-only
	STATUS     current
	DESCRIPTION
		"Reserved."
	::= { powerSupply6BasicInfo 1 }

powerSupply6InfoProductName              OBJECT-TYPE
	SYNTAX     DisplayString
	MAX-ACCESS read-only
	STATUS     current
	DESCRIPTION
		"This shows the product name of power supply module6."
	::= { powerSupply6BasicInfo 2 }

powerSupply6InfoModel                    OBJECT-TYPE
	SYNTAX     DisplayString
	MAX-ACCESS read-only
	STATUS     current
	DESCRIPTION
		"This shows the model name of power supply module6."
	::= { powerSupply6BasicInfo 3 }

powerSupply6InfoSerialNum                OBJECT-TYPE
	SYNTAX     DisplayString
	MAX-ACCESS read-only
	STATUS     current
	DESCRIPTION
		"This shows the serial number of power supply module6."
	::= { powerSupply6BasicInfo 4 }

powerSupply6InfoProductVersion           OBJECT-TYPE
	SYNTAX     DisplayString
	MAX-ACCESS read-only
	STATUS     current
	DESCRIPTION
		"This shows the product version of power supply module6."
	::= { powerSupply6BasicInfo 5 }

powerSupply6InfoProductManufacturer      OBJECT-TYPE
	SYNTAX     DisplayString
	MAX-ACCESS read-only
	STATUS     current
	DESCRIPTION
		"This shows the product manufacturer of power supply module6."
	::= { powerSupply6BasicInfo 6 }

powerSupply6InfoBoardProductName         OBJECT-TYPE
	SYNTAX     DisplayString
	MAX-ACCESS read-only
	STATUS     current
	DESCRIPTION
		"Reserved."
	::= { powerSupply6BasicInfo 7 }

powerSupply6InfoBoardSerialNum           OBJECT-TYPE
	SYNTAX     DisplayString
	MAX-ACCESS read-only
	STATUS     current
	DESCRIPTION
		"Reserved."
	::= { powerSupply6BasicInfo 8 }

powerSupply6InfoBoardManufacturer        OBJECT-TYPE
	SYNTAX     DisplayString
	MAX-ACCESS read-only
	STATUS     current
	DESCRIPTION
		"Reserved."
	::= { powerSupply6BasicInfo 9 }

powerSupply6InfoSpec                     OBJECT IDENTIFIER ::= { powerSupply6BasicInfo 20 }

powerSupply6SpecRateVoltageMain          OBJECT-TYPE
	SYNTAX     Integer32
	UNITS      "0.1 V"
	MAX-ACCESS read-only
	STATUS     current
	DESCRIPTION
		"This shows the rated voltage of power supply module6.(main)"
	::= { powerSupply6InfoSpec 1 }

powerSupply6SpecRateVoltageSub           OBJECT-TYPE
	SYNTAX     Integer32
	UNITS      "0.1 V"
	MAX-ACCESS read-only
	STATUS     current
	DESCRIPTION
		"This shows the rated voltage of power supply module6.(sub)"
	::= { powerSupply6InfoSpec 2 }

powerSupply6SpecAmbientTempUpperLimit    OBJECT-TYPE
	SYNTAX     Integer32
	UNITS      "0.1 degrees C"
	MAX-ACCESS read-only
	STATUS     current
	DESCRIPTION
		"This shows the highest temperature of ambient in power supply module."
	::= { powerSupply6InfoSpec 3 }

powerSupply6SpecAmbientTempLowerLimit    OBJECT-TYPE
	SYNTAX     Integer32
	UNITS      "0.1 degrees C"
	MAX-ACCESS read-only
	STATUS     current
	DESCRIPTION
		"This shows the lowest temperature of ambient in power supply module."
	::= { powerSupply6InfoSpec 4 }

powerSupply6SpecHotSpotTempUpperLimit    OBJECT-TYPE
	SYNTAX     Integer32
	UNITS      "0.1 degrees C"
	MAX-ACCESS read-only
	STATUS     current
	DESCRIPTION
		"This shows the highest temperature of hot spot in power supply module."
	::= { powerSupply6InfoSpec 5 }

powerSupply6SpecHotSpotTempLowerLimit    OBJECT-TYPE
	SYNTAX     Integer32
	UNITS      "0.1 degrees C"
	MAX-ACCESS read-only
	STATUS     current
	DESCRIPTION
		"This shows the lowest temperature of hot spot in power supply module."
	::= { powerSupply6InfoSpec 6 }

powerSupply6SpecExhaustTempUpperLimit    OBJECT-TYPE
	SYNTAX     Integer32
	UNITS      "0.1 degrees C"
	MAX-ACCESS read-only
	STATUS     current
	DESCRIPTION
		"This shows the highest temperature of exhaust in power supply module."
	::= { powerSupply6InfoSpec 7 }

powerSupply6SpecExhaustTempLowerLimit    OBJECT-TYPE
	SYNTAX     Integer32
	UNITS      "0.1 degrees C"
	MAX-ACCESS read-only
	STATUS     current
	DESCRIPTION
		"This shows the lowest temperature of exhaust in power supply module."
	::= { powerSupply6InfoSpec 8 }

powerSupply6Capacity                     OBJECT IDENTIFIER ::= { powerSupply6 2 }

powerSupply6CapacityFan                  OBJECT-TYPE
	SYNTAX     Integer32
	MAX-ACCESS read-only
	STATUS     current
	DESCRIPTION
		"This shows the capacity fans of power supply module6."
	::= { powerSupply6Capacity 1 }

powerSupply6Settings                     OBJECT-TYPE
	SYNTAX     DisplayString
	MAX-ACCESS read-only
	STATUS     current
	DESCRIPTION
		"Reserved."
	::= { powerSupply6 3 }

powerSupply6State                        OBJECT IDENTIFIER ::= { powerSupply6 4 }

powerSupply6StateSlotNum                 OBJECT-TYPE
	SYNTAX     Integer32
	MAX-ACCESS read-only
	STATUS     current
	DESCRIPTION
		"This shows the number of installed slots of power supply module6."
	::= { powerSupply6State 1 }

powerSupply6StatePower                   OBJECT-TYPE
	SYNTAX     INTEGER {
		poweroff(1), poweron(2), unknown(3)
	}
	MAX-ACCESS read-only
	STATUS     current
	DESCRIPTION
		"This shows the power supply state of power supply module6."
	::= { powerSupply6State 2 }

powerSupply6StateHealth                  OBJECT-TYPE
	SYNTAX     INTEGER {
		normal(1), fail(2), unknown(3)
	}
	MAX-ACCESS read-only
	STATUS     current
	DESCRIPTION
		"This shows the health state of power supply module6."
	::= { powerSupply6State 3 }

powerSupply6StateAmbientTemp             OBJECT-TYPE
	SYNTAX     Integer32
	UNITS      "0.1 degrees C"
	MAX-ACCESS read-only
	STATUS     current
	DESCRIPTION
		"This shows the temperature value of ambient sensor of power supply module6."
	::= { powerSupply6State 4 }

powerSupply6StateHotSpotTemp             OBJECT-TYPE
	SYNTAX     Integer32
	UNITS      "0.1 degrees C"
	MAX-ACCESS read-only
	STATUS     current
	DESCRIPTION
		"This shows the temperature value of hot spot sensor of power supply module6."
	::= { powerSupply6State 5 }

powerSupply6StateExhaustTemp             OBJECT-TYPE
	SYNTAX     Integer32
	UNITS      "0.1 degrees C"
	MAX-ACCESS read-only
	STATUS     current
	DESCRIPTION
		"This shows the temperature value of exhaust sensor of power supply module."
	::= { powerSupply6State 6 }

powerSupply6StateMainVoltage             OBJECT-TYPE
	SYNTAX     Integer32
	UNITS      "0.1 V"
	MAX-ACCESS read-only
	STATUS     current
	DESCRIPTION
		"This shows the main voltage of power supply module6."
	::= { powerSupply6State 7 }

powerSupply6StateSubVoltage              OBJECT-TYPE
	SYNTAX     Integer32
	UNITS      "0.1 V"
	MAX-ACCESS read-only
	STATUS     current
	DESCRIPTION
		"This shows the sub voltage of power supply module6."
	::= { powerSupply6State 8 }

powerSupply6StateInputVoltage            OBJECT-TYPE
	SYNTAX     Integer32
	UNITS      "0.1 V"
	MAX-ACCESS read-only
	STATUS     current
	DESCRIPTION
		"This shows the input voltage of power supply module6."
	::= { powerSupply6State 9 }

powerSupply6StateMainCurrent             OBJECT-TYPE
	SYNTAX     Integer32
	UNITS      "0.1 A"
	MAX-ACCESS read-only
	STATUS     current
	DESCRIPTION
		"This shows the main current of power supply module6."
	::= { powerSupply6State 10 }

powerSupply6StateSubCurrent              OBJECT-TYPE
	SYNTAX     Integer32
	UNITS      "0.1 A"
	MAX-ACCESS read-only
	STATUS     current
	DESCRIPTION
		"This shows the sub current of power supply module6."
	::= { powerSupply6State 11 }

powerSupply6StateInputCurrent            OBJECT-TYPE
	SYNTAX     Integer32
	UNITS      "0.1 A"
	MAX-ACCESS read-only
	STATUS     current
	DESCRIPTION
		"This shows the input current of power supply module6."
	::= { powerSupply6State 12 }

powerSupply6StateLEDTable                OBJECT-TYPE
	SYNTAX SEQUENCE OF powerSupply6StateLEDEntry
	MAX-ACCESS not-accessible
	STATUS     current
	DESCRIPTION
		"Reserved."
	::= { powerSupply6State 13 }

powerSupply6StateLEDEntry                OBJECT-TYPE
	SYNTAX     PowerSupply6StateLEDEntry
	MAX-ACCESS not-accessible
	STATUS     current
	DESCRIPTION
		"Reserved."
	INDEX { powerSupply6StateLEDIndex }
	::= { powerSupply6StateLEDTable 1 }

PowerSupply6StateLEDEntry ::= SEQUENCE {
	powerSupply6StateLEDIndex
		Integer32,
	powerSupply6StateLEDName
		DisplayString,
	powerSupply6StateLEDType
		DisplayString,
	powerSupply6StateLEDState
		DisplayString,
	powerSupply6StateLEDColor
		DisplayString
}

powerSupply6StateLEDIndex                OBJECT-TYPE
	SYNTAX     Integer32
	MAX-ACCESS read-only
	STATUS     current
	DESCRIPTION
		"Reserved."
	::= { powerSupply6StateLEDEntry 1 }

powerSupply6StateLEDName                 OBJECT-TYPE
	SYNTAX     DisplayString
	MAX-ACCESS read-only
	STATUS     current
	DESCRIPTION
		"Reserved."
	::= { powerSupply6StateLEDEntry 2 }

powerSupply6StateLEDType                 OBJECT-TYPE
	SYNTAX     DisplayString
	MAX-ACCESS read-only
	STATUS     current
	DESCRIPTION
		"Reserved."
	::= { powerSupply6StateLEDEntry 3 }

powerSupply6StateLEDState                OBJECT-TYPE
	SYNTAX     DisplayString
	MAX-ACCESS read-only
	STATUS     current
	DESCRIPTION
		"Reserved."
	::= { powerSupply6StateLEDEntry 4 }

powerSupply6StateLEDColor                OBJECT-TYPE
	SYNTAX     DisplayString
	MAX-ACCESS read-only
	STATUS     current
	DESCRIPTION
		"Reserved."
	::= { powerSupply6StateLEDEntry 5 }

powerSupply6StateFanTable                OBJECT-TYPE
	SYNTAX SEQUENCE OF powerSupply6StateFanEntry
	MAX-ACCESS not-accessible
	STATUS     current
	DESCRIPTION
		"This shows the table of fan of power supply module6."
	::= { powerSupply6State 14 }

powerSupply6StateFanEntry                OBJECT-TYPE
	SYNTAX     PowerSupply6StateFanEntry
	MAX-ACCESS not-accessible
	STATUS     current
	DESCRIPTION
		"This shows the entry of fan of power supply module6."
	INDEX { powerSupply6StateFanIndex }
	::= { powerSupply6StateFanTable 1 }

PowerSupply6StateFanEntry ::= SEQUENCE {
	powerSupply6StateFanIndex
		Integer32,
	powerSupply6StateFanLocation
		DisplayString,
	powerSupply6StateFanRPM
		Integer32
}

powerSupply6StateFanIndex                OBJECT-TYPE
	SYNTAX     Integer32
	MAX-ACCESS read-only
	STATUS     current
	DESCRIPTION
		"This shows the index of fan of power supply module6."
	::= { powerSupply6StateFanEntry 1 }

powerSupply6StateFanLocation             OBJECT-TYPE
	SYNTAX     DisplayString
	MAX-ACCESS read-only
	STATUS     current
	DESCRIPTION
		"This shows the location of fan of power supply module6."
	::= { powerSupply6StateFanEntry 2 }

powerSupply6StateFanRPM                  OBJECT-TYPE
	SYNTAX     Integer32
	UNITS      "rpm"
	MAX-ACCESS read-only
	STATUS     current
	DESCRIPTION
		"This shows the rpm value of power supply module6."
	::= { powerSupply6StateFanEntry 3 }

partition                                OBJECT IDENTIFIER ::= { computeRack 3 }

partition1                               OBJECT IDENTIFIER ::= { partition 1 }

partition1BasicInfo                      OBJECT IDENTIFIER ::= { partition1 1 }

partition1Valid                          OBJECT-TYPE
	SYNTAX     INTEGER {
		invalid(1), valid(2), unknown(3)
	}
	MAX-ACCESS read-only
	STATUS     current
	DESCRIPTION
		"This shows the validity of information of partition1."
	::= { partition1BasicInfo 1 }

partition1MaxCurrent                     OBJECT-TYPE
	SYNTAX     Integer32
	UNITS      "0.1 A"
	MAX-ACCESS read-only
	STATUS     current
	DESCRIPTION
		"This shows the maximum current of partition1."
	::= { partition1BasicInfo 2 }

partition1MaxPower                       OBJECT-TYPE
	SYNTAX     Integer32
	UNITS      "W"
	MAX-ACCESS read-only
	STATUS     current
	DESCRIPTION
		"This shows the maximum power of partition1."
	::= { partition1BasicInfo 3 }

partition1ProcCoreCount                  OBJECT-TYPE
	SYNTAX     Integer32
	MAX-ACCESS read-only
	STATUS     current
	DESCRIPTION
		"This shows the total number of CPU core of partition1."
	::= { partition1BasicInfo 4 }

partition1DIMMCapacity                   OBJECT-TYPE
	SYNTAX     Integer32
	UNITS      "GB"
	MAX-ACCESS read-only
	STATUS     current
	DESCRIPTION
		"This shows the total amount of DIMM capacity of partition1."
	::= { partition1BasicInfo 5 }

partition1HVMLicence                     OBJECT-TYPE
	SYNTAX     DisplayString
	MAX-ACCESS read-only
	STATUS     current
	DESCRIPTION
		"This shows the HVM licence information of partition1."
	::= { partition1BasicInfo 6 }

partition1Settings                       OBJECT IDENTIFIER ::= { partition1 3 }

partition1SettingsSystemMode             OBJECT-TYPE
	SYNTAX     INTEGER {
		basic(1), hvm(2), unknown(3)
	}
	MAX-ACCESS read-only
	STATUS     current
	DESCRIPTION
		"This shows the hvm mode setting of partition1."
	::= { partition1Settings 1 }

partition1SettingsDIMMRedundancy         OBJECT-TYPE
	SYNTAX     INTEGER {
		redundancy(1), non-redundancy(2), unknown(3)
	}
	MAX-ACCESS read-only
	STATUS     current
	DESCRIPTION
		"This shows the DIMM redundancy of partition1."
	::= { partition1Settings 2 }

partition1State                          OBJECT IDENTIFIER ::= { partition1 4 }

partition1StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition1."
	::= { partition1State 1 }

partition1StateHealth                    OBJECT-TYPE
	SYNTAX     INTEGER {
		normal(1), fail(2), unknown(3)
	}
	MAX-ACCESS read-only
	STATUS     current
	DESCRIPTION
		"This shows the health state of partition1."
	::= { partition1State 2 }

partition1StateSystemMode                OBJECT-TYPE
	SYNTAX     INTEGER {
		basic(1), hvm(2), unknown(3)
	}
	MAX-ACCESS read-only
	STATUS     current
	DESCRIPTION
		"This shows the hvm mode of partition1."
	::= { partition1State 3 }

partition1StateCunsumptionCurrent        OBJECT-TYPE
	SYNTAX     Integer32
	UNITS      "0.1 A"
	MAX-ACCESS read-only
	STATUS     current
	DESCRIPTION
		"This shows the consumption current of partition1."
	::= { partition1State 4 }

partition1StatePowerConsumption          OBJECT-TYPE
	SYNTAX     Integer32
	UNITS      "W"
	MAX-ACCESS read-only
	STATUS     current
	DESCRIPTION
		"This shows the current power consumption of partition1."
	::= { partition1State 5 }

partition2                               OBJECT IDENTIFIER ::= { partition 2 }

partition2BasicInfo                      OBJECT IDENTIFIER ::= { partition2 1 }

partition2Valid                          OBJECT-TYPE
	SYNTAX     INTEGER {
		invalid(1), valid(2), unknown(3)
	}
	MAX-ACCESS read-only
	STATUS     current
	DESCRIPTION
		"This shows the validity of information of partition2."
	::= { partition2BasicInfo 1 }

partition2MaxCurrent                     OBJECT-TYPE
	SYNTAX     Integer32
	UNITS      "0.1 A"
	MAX-ACCESS read-only
	STATUS     current
	DESCRIPTION
		"This shows the maximum current of partition2."
	::= { partition2BasicInfo 2 }

partition2MaxPower                       OBJECT-TYPE
	SYNTAX     Integer32
	UNITS      "W"
	MAX-ACCESS read-only
	STATUS     current
	DESCRIPTION
		"This shows the maximum power of partition2."
	::= { partition2BasicInfo 3 }

partition2ProcCoreCount                  OBJECT-TYPE
	SYNTAX     Integer32
	MAX-ACCESS read-only
	STATUS     current
	DESCRIPTION
		"This shows the total number of CPU core of partition2."
	::= { partition2BasicInfo 4 }

partition2DIMMCapacity                   OBJECT-TYPE
	SYNTAX     Integer32
	UNITS      "GB"
	MAX-ACCESS read-only
	STATUS     current
	DESCRIPTION
		"This shows the total amount of DIMM capacity of partition2."
	::= { partition2BasicInfo 5 }

partition2HVMLicence                     OBJECT-TYPE
	SYNTAX     DisplayString
	MAX-ACCESS read-only
	STATUS     current
	DESCRIPTION
		"This shows the HVM licence information of partition2."
	::= { partition2BasicInfo 6 }

partition2Settings                       OBJECT IDENTIFIER ::= { partition2 3 }

partition2SettingsSystemMode             OBJECT-TYPE
	SYNTAX     INTEGER {
		basic(1), hvm(2), unknown(3)
	}
	MAX-ACCESS read-only
	STATUS     current
	DESCRIPTION
		"This shows the hvm mode setting of partition2."
	::= { partition2Settings 1 }

partition2SettingsDIMMRedundancy         OBJECT-TYPE
	SYNTAX     INTEGER {
		redundancy(1), non-redundancy(2), unknown(3)
	}
	MAX-ACCESS read-only
	STATUS     current
	DESCRIPTION
		"This shows the DIMM redundancy of partition2."
	::= { partition2Settings 2 }

partition2State                          OBJECT IDENTIFIER ::= { partition2 4 }

partition2StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition2."
	::= { partition2State 1 }

partition2StateHealth                    OBJECT-TYPE
	SYNTAX     INTEGER {
		normal(1), fail(2), unknown(3)
	}
	MAX-ACCESS read-only
	STATUS     current
	DESCRIPTION
		"This shows the health state of partition2."
	::= { partition2State 2 }

partition2StateSystemMode                OBJECT-TYPE
	SYNTAX     INTEGER {
		basic(1), hvm(2), unknown(3)
	}
	MAX-ACCESS read-only
	STATUS     current
	DESCRIPTION
		"This shows the hvm mode of partition2."
	::= { partition2State 3 }

partition2StateCunsumptionCurrent        OBJECT-TYPE
	SYNTAX     Integer32
	UNITS      "0.1 A"
	MAX-ACCESS read-only
	STATUS     current
	DESCRIPTION
		"This shows the consumption current of partition2."
	::= { partition2State 4 }

partition2StatePowerConsumption          OBJECT-TYPE
	SYNTAX     Integer32
	UNITS      "W"
	MAX-ACCESS read-only
	STATUS     current
	DESCRIPTION
		"This shows the current power consumption of partition2."
	::= { partition2State 5 }

partition3                               OBJECT IDENTIFIER ::= { partition 3 }

partition3BasicInfo                      OBJECT IDENTIFIER ::= { partition3 1 }

partition3Valid                          OBJECT-TYPE
	SYNTAX     INTEGER {
		invalid(1), valid(2), unknown(3)
	}
	MAX-ACCESS read-only
	STATUS     current
	DESCRIPTION
		"This shows the validity of information of partition3."
	::= { partition3BasicInfo 1 }

partition3MaxCurrent                     OBJECT-TYPE
	SYNTAX     Integer32
	UNITS      "0.1 A"
	MAX-ACCESS read-only
	STATUS     current
	DESCRIPTION
		"This shows the maximum current of partition3."
	::= { partition3BasicInfo 2 }

partition3MaxPower                       OBJECT-TYPE
	SYNTAX     Integer32
	UNITS      "W"
	MAX-ACCESS read-only
	STATUS     current
	DESCRIPTION
		"This shows the maximum power of partition3."
	::= { partition3BasicInfo 3 }

partition3ProcCoreCount                  OBJECT-TYPE
	SYNTAX     Integer32
	MAX-ACCESS read-only
	STATUS     current
	DESCRIPTION
		"This shows the total number of CPU core of partition3."
	::= { partition3BasicInfo 4 }

partition3DIMMCapacity                   OBJECT-TYPE
	SYNTAX     Integer32
	UNITS      "GB"
	MAX-ACCESS read-only
	STATUS     current
	DESCRIPTION
		"This shows the total amount of DIMM capacity of partition3."
	::= { partition3BasicInfo 5 }

partition3HVMLicence                     OBJECT-TYPE
	SYNTAX     DisplayString
	MAX-ACCESS read-only
	STATUS     current
	DESCRIPTION
		"This shows the HVM licence information of partition3."
	::= { partition3BasicInfo 6 }

partition3Settings                       OBJECT IDENTIFIER ::= { partition3 3 }

partition3SettingsSystemMode             OBJECT-TYPE
	SYNTAX     INTEGER {
		basic(1), hvm(2), unknown(3)
	}
	MAX-ACCESS read-only
	STATUS     current
	DESCRIPTION
		"This shows the hvm mode setting of partition3."
	::= { partition3Settings 1 }

partition3SettingsDIMMRedundancy         OBJECT-TYPE
	SYNTAX     INTEGER {
		redundancy(1), non-redundancy(2), unknown(3)
	}
	MAX-ACCESS read-only
	STATUS     current
	DESCRIPTION
		"This shows the DIMM redundancy of partition3."
	::= { partition3Settings 2 }

partition3State                          OBJECT IDENTIFIER ::= { partition3 4 }

partition3StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition3."
	::= { partition3State 1 }

partition3StateHealth                    OBJECT-TYPE
	SYNTAX     INTEGER {
		normal(1), fail(2), unknown(3)
	}
	MAX-ACCESS read-only
	STATUS     current
	DESCRIPTION
		"This shows the health state of partition3."
	::= { partition3State 2 }

partition3StateSystemMode                OBJECT-TYPE
	SYNTAX     INTEGER {
		basic(1), hvm(2), unknown(3)
	}
	MAX-ACCESS read-only
	STATUS     current
	DESCRIPTION
		"This shows the hvm mode of partition3."
	::= { partition3State 3 }

partition3StateCunsumptionCurrent        OBJECT-TYPE
	SYNTAX     Integer32
	UNITS      "0.1 A"
	MAX-ACCESS read-only
	STATUS     current
	DESCRIPTION
		"This shows the consumption current of partition3."
	::= { partition3State 4 }

partition3StatePowerConsumption          OBJECT-TYPE
	SYNTAX     Integer32
	UNITS      "W"
	MAX-ACCESS read-only
	STATUS     current
	DESCRIPTION
		"This shows the current power consumption of partition3."
	::= { partition3State 5 }

partition4                               OBJECT IDENTIFIER ::= { partition 4 }

partition4BasicInfo                      OBJECT IDENTIFIER ::= { partition4 1 }

partition4Valid                          OBJECT-TYPE
	SYNTAX     INTEGER {
		invalid(1), valid(2), unknown(3)
	}
	MAX-ACCESS read-only
	STATUS     current
	DESCRIPTION
		"This shows the validity of information of partition4."
	::= { partition4BasicInfo 1 }

partition4MaxCurrent                     OBJECT-TYPE
	SYNTAX     Integer32
	UNITS      "0.1 A"
	MAX-ACCESS read-only
	STATUS     current
	DESCRIPTION
		"This shows the maximum current of partition4."
	::= { partition4BasicInfo 2 }

partition4MaxPower                       OBJECT-TYPE
	SYNTAX     Integer32
	UNITS      "W"
	MAX-ACCESS read-only
	STATUS     current
	DESCRIPTION
		"This shows the maximum power of partition4."
	::= { partition4BasicInfo 3 }

partition4ProcCoreCount                  OBJECT-TYPE
	SYNTAX     Integer32
	MAX-ACCESS read-only
	STATUS     current
	DESCRIPTION
		"This shows the total number of CPU core of partition4."
	::= { partition4BasicInfo 4 }

partition4DIMMCapacity                   OBJECT-TYPE
	SYNTAX     Integer32
	UNITS      "GB"
	MAX-ACCESS read-only
	STATUS     current
	DESCRIPTION
		"This shows the total amount of DIMM capacity of partition4."
	::= { partition4BasicInfo 5 }

partition4HVMLicence                     OBJECT-TYPE
	SYNTAX     DisplayString
	MAX-ACCESS read-only
	STATUS     current
	DESCRIPTION
		"This shows the HVM licence information of partition4."
	::= { partition4BasicInfo 6 }

partition4Settings                       OBJECT IDENTIFIER ::= { partition4 3 }

partition4SettingsSystemMode             OBJECT-TYPE
	SYNTAX     INTEGER {
		basic(1), hvm(2), unknown(3)
	}
	MAX-ACCESS read-only
	STATUS     current
	DESCRIPTION
		"This shows the hvm mode setting of partition4."
	::= { partition4Settings 1 }

partition4SettingsDIMMRedundancy         OBJECT-TYPE
	SYNTAX     INTEGER {
		redundancy(1), non-redundancy(2), unknown(3)
	}
	MAX-ACCESS read-only
	STATUS     current
	DESCRIPTION
		"This shows the DIMM redundancy of partition4."
	::= { partition4Settings 2 }

partition4State                          OBJECT IDENTIFIER ::= { partition4 4 }

partition4StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition4."
	::= { partition4State 1 }

partition4StateHealth                    OBJECT-TYPE
	SYNTAX     INTEGER {
		normal(1), fail(2), unknown(3)
	}
	MAX-ACCESS read-only
	STATUS     current
	DESCRIPTION
		"This shows the health state of partition4."
	::= { partition4State 2 }

partition4StateSystemMode                OBJECT-TYPE
	SYNTAX     INTEGER {
		basic(1), hvm(2), unknown(3)
	}
	MAX-ACCESS read-only
	STATUS     current
	DESCRIPTION
		"This shows the hvm mode of partition4."
	::= { partition4State 3 }

partition4StateCunsumptionCurrent        OBJECT-TYPE
	SYNTAX     Integer32
	UNITS      "0.1 A"
	MAX-ACCESS read-only
	STATUS     current
	DESCRIPTION
		"This shows the consumption current of partition4."
	::= { partition4State 4 }

partition4StatePowerConsumption          OBJECT-TYPE
	SYNTAX     Integer32
	UNITS      "W"
	MAX-ACCESS read-only
	STATUS     current
	DESCRIPTION
		"This shows the current power consumption of partition4."
	::= { partition4State 5 }

partition5                               OBJECT IDENTIFIER ::= { partition 5 }

partition5BasicInfo                      OBJECT IDENTIFIER ::= { partition5 1 }

partition5Valid                          OBJECT-TYPE
	SYNTAX     INTEGER {
		invalid(1), valid(2), unknown(3)
	}
	MAX-ACCESS read-only
	STATUS     current
	DESCRIPTION
		"This shows the validity of information of partition5."
	::= { partition5BasicInfo 1 }

partition5MaxCurrent                     OBJECT-TYPE
	SYNTAX     Integer32
	UNITS      "0.1 A"
	MAX-ACCESS read-only
	STATUS     current
	DESCRIPTION
		"This shows the maximum current of partition5."
	::= { partition5BasicInfo 2 }

partition5MaxPower                       OBJECT-TYPE
	SYNTAX     Integer32
	UNITS      "W"
	MAX-ACCESS read-only
	STATUS     current
	DESCRIPTION
		"This shows the maximum power of partition5."
	::= { partition5BasicInfo 3 }

partition5ProcCoreCount                  OBJECT-TYPE
	SYNTAX     Integer32
	MAX-ACCESS read-only
	STATUS     current
	DESCRIPTION
		"This shows the total number of CPU core of partition5."
	::= { partition5BasicInfo 4 }

partition5DIMMCapacity                   OBJECT-TYPE
	SYNTAX     Integer32
	UNITS      "GB"
	MAX-ACCESS read-only
	STATUS     current
	DESCRIPTION
		"This shows the total amount of DIMM capacity of partition5."
	::= { partition5BasicInfo 5 }

partition5HVMLicence                     OBJECT-TYPE
	SYNTAX     DisplayString
	MAX-ACCESS read-only
	STATUS     current
	DESCRIPTION
		"This shows the HVM licence information of partition5."
	::= { partition5BasicInfo 6 }

partition5Settings                       OBJECT IDENTIFIER ::= { partition5 3 }

partition5SettingsSystemMode             OBJECT-TYPE
	SYNTAX     INTEGER {
		basic(1), hvm(2), unknown(3)
	}
	MAX-ACCESS read-only
	STATUS     current
	DESCRIPTION
		"This shows the hvm mode setting of partition5."
	::= { partition5Settings 1 }

partition5SettingsDIMMRedundancy         OBJECT-TYPE
	SYNTAX     INTEGER {
		redundancy(1), non-redundancy(2), unknown(3)
	}
	MAX-ACCESS read-only
	STATUS     current
	DESCRIPTION
		"This shows the DIMM redundancy of partition5."
	::= { partition5Settings 2 }

partition5State                          OBJECT IDENTIFIER ::= { partition5 4 }

partition5StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition5."
	::= { partition5State 1 }

partition5StateHealth                    OBJECT-TYPE
	SYNTAX     INTEGER {
		normal(1), fail(2), unknown(3)
	}
	MAX-ACCESS read-only
	STATUS     current
	DESCRIPTION
		"This shows the health state of partition5."
	::= { partition5State 2 }

partition5StateSystemMode                OBJECT-TYPE
	SYNTAX     INTEGER {
		basic(1), hvm(2), unknown(3)
	}
	MAX-ACCESS read-only
	STATUS     current
	DESCRIPTION
		"This shows the hvm mode of partition5."
	::= { partition5State 3 }

partition5StateCunsumptionCurrent        OBJECT-TYPE
	SYNTAX     Integer32
	UNITS      "0.1 A"
	MAX-ACCESS read-only
	STATUS     current
	DESCRIPTION
		"This shows the consumption current of partition5."
	::= { partition5State 4 }

partition5StatePowerConsumption          OBJECT-TYPE
	SYNTAX     Integer32
	UNITS      "W"
	MAX-ACCESS read-only
	STATUS     current
	DESCRIPTION
		"This shows the current power consumption of partition5."
	::= { partition5State 5 }

partition6                               OBJECT IDENTIFIER ::= { partition 6 }

partition6BasicInfo                      OBJECT IDENTIFIER ::= { partition6 1 }

partition6Valid                          OBJECT-TYPE
	SYNTAX     INTEGER {
		invalid(1), valid(2), unknown(3)
	}
	MAX-ACCESS read-only
	STATUS     current
	DESCRIPTION
		"This shows the validity of information of partition6."
	::= { partition6BasicInfo 1 }

partition6MaxCurrent                     OBJECT-TYPE
	SYNTAX     Integer32
	UNITS      "0.1 A"
	MAX-ACCESS read-only
	STATUS     current
	DESCRIPTION
		"This shows the maximum current of partition6."
	::= { partition6BasicInfo 2 }

partition6MaxPower                       OBJECT-TYPE
	SYNTAX     Integer32
	UNITS      "W"
	MAX-ACCESS read-only
	STATUS     current
	DESCRIPTION
		"This shows the maximum power of partition6."
	::= { partition6BasicInfo 3 }

partition6ProcCoreCount                  OBJECT-TYPE
	SYNTAX     Integer32
	MAX-ACCESS read-only
	STATUS     current
	DESCRIPTION
		"This shows the total number of CPU core of partition6."
	::= { partition6BasicInfo 4 }

partition6DIMMCapacity                   OBJECT-TYPE
	SYNTAX     Integer32
	UNITS      "GB"
	MAX-ACCESS read-only
	STATUS     current
	DESCRIPTION
		"This shows the total amount of DIMM capacity of partition6."
	::= { partition6BasicInfo 5 }

partition6HVMLicence                     OBJECT-TYPE
	SYNTAX     DisplayString
	MAX-ACCESS read-only
	STATUS     current
	DESCRIPTION
		"This shows the HVM licence information of partition6."
	::= { partition6BasicInfo 6 }

partition6Settings                       OBJECT IDENTIFIER ::= { partition6 3 }

partition6SettingsSystemMode             OBJECT-TYPE
	SYNTAX     INTEGER {
		basic(1), hvm(2), unknown(3)
	}
	MAX-ACCESS read-only
	STATUS     current
	DESCRIPTION
		"This shows the hvm mode setting of partition6."
	::= { partition6Settings 1 }

partition6SettingsDIMMRedundancy         OBJECT-TYPE
	SYNTAX     INTEGER {
		redundancy(1), non-redundancy(2), unknown(3)
	}
	MAX-ACCESS read-only
	STATUS     current
	DESCRIPTION
		"This shows the DIMM redundancy of partition6."
	::= { partition6Settings 2 }

partition6State                          OBJECT IDENTIFIER ::= { partition6 4 }

partition6StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition6."
	::= { partition6State 1 }

partition6StateHealth                    OBJECT-TYPE
	SYNTAX     INTEGER {
		normal(1), fail(2), unknown(3)
	}
	MAX-ACCESS read-only
	STATUS     current
	DESCRIPTION
		"This shows the health state of partition6."
	::= { partition6State 2 }

partition6StateSystemMode                OBJECT-TYPE
	SYNTAX     INTEGER {
		basic(1), hvm(2), unknown(3)
	}
	MAX-ACCESS read-only
	STATUS     current
	DESCRIPTION
		"This shows the hvm mode of partition6."
	::= { partition6State 3 }

partition6StateCunsumptionCurrent        OBJECT-TYPE
	SYNTAX     Integer32
	UNITS      "0.1 A"
	MAX-ACCESS read-only
	STATUS     current
	DESCRIPTION
		"This shows the consumption current of partition6."
	::= { partition6State 4 }

partition6StatePowerConsumption          OBJECT-TYPE
	SYNTAX     Integer32
	UNITS      "W"
	MAX-ACCESS read-only
	STATUS     current
	DESCRIPTION
		"This shows the current power consumption of partition6."
	::= { partition6State 5 }

partition7                               OBJECT IDENTIFIER ::= { partition 7 }

partition7BasicInfo                      OBJECT IDENTIFIER ::= { partition7 1 }

partition7Valid                          OBJECT-TYPE
	SYNTAX     INTEGER {
		invalid(1), valid(2), unknown(3)
	}
	MAX-ACCESS read-only
	STATUS     current
	DESCRIPTION
		"This shows the validity of information of partition7."
	::= { partition7BasicInfo 1 }

partition7MaxCurrent                     OBJECT-TYPE
	SYNTAX     Integer32
	UNITS      "0.1 A"
	MAX-ACCESS read-only
	STATUS     current
	DESCRIPTION
		"This shows the maximum current of partition7."
	::= { partition7BasicInfo 2 }

partition7MaxPower                       OBJECT-TYPE
	SYNTAX     Integer32
	UNITS      "W"
	MAX-ACCESS read-only
	STATUS     current
	DESCRIPTION
		"This shows the maximum power of partition7."
	::= { partition7BasicInfo 3 }

partition7ProcCoreCount                  OBJECT-TYPE
	SYNTAX     Integer32
	MAX-ACCESS read-only
	STATUS     current
	DESCRIPTION
		"This shows the total number of CPU core of partition7."
	::= { partition7BasicInfo 4 }

partition7DIMMCapacity                   OBJECT-TYPE
	SYNTAX     Integer32
	UNITS      "GB"
	MAX-ACCESS read-only
	STATUS     current
	DESCRIPTION
		"This shows the total amount of DIMM capacity of partition7."
	::= { partition7BasicInfo 5 }

partition7HVMLicence                     OBJECT-TYPE
	SYNTAX     DisplayString
	MAX-ACCESS read-only
	STATUS     current
	DESCRIPTION
		"This shows the HVM licence information of partition7."
	::= { partition7BasicInfo 6 }

partition7Settings                       OBJECT IDENTIFIER ::= { partition7 3 }

partition7SettingsSystemMode             OBJECT-TYPE
	SYNTAX     INTEGER {
		basic(1), hvm(2), unknown(3)
	}
	MAX-ACCESS read-only
	STATUS     current
	DESCRIPTION
		"This shows the hvm mode setting of partition7."
	::= { partition7Settings 1 }

partition7SettingsDIMMRedundancy         OBJECT-TYPE
	SYNTAX     INTEGER {
		redundancy(1), non-redundancy(2), unknown(3)
	}
	MAX-ACCESS read-only
	STATUS     current
	DESCRIPTION
		"This shows the DIMM redundancy of partition7."
	::= { partition7Settings 2 }

partition7State                          OBJECT IDENTIFIER ::= { partition7 4 }

partition7StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition7."
	::= { partition7State 1 }

partition7StateHealth                    OBJECT-TYPE
	SYNTAX     INTEGER {
		normal(1), fail(2), unknown(3)
	}
	MAX-ACCESS read-only
	STATUS     current
	DESCRIPTION
		"This shows the health state of partition7."
	::= { partition7State 2 }

partition7StateSystemMode                OBJECT-TYPE
	SYNTAX     INTEGER {
		basic(1), hvm(2), unknown(3)
	}
	MAX-ACCESS read-only
	STATUS     current
	DESCRIPTION
		"This shows the hvm mode of partition7."
	::= { partition7State 3 }

partition7StateCunsumptionCurrent        OBJECT-TYPE
	SYNTAX     Integer32
	UNITS      "0.1 A"
	MAX-ACCESS read-only
	STATUS     current
	DESCRIPTION
		"This shows the consumption current of partition7."
	::= { partition7State 4 }

partition7StatePowerConsumption          OBJECT-TYPE
	SYNTAX     Integer32
	UNITS      "W"
	MAX-ACCESS read-only
	STATUS     current
	DESCRIPTION
		"This shows the current power consumption of partition7."
	::= { partition7State 5 }

partition8                               OBJECT IDENTIFIER ::= { partition 8 }

partition8BasicInfo                      OBJECT IDENTIFIER ::= { partition8 1 }

partition8Valid                          OBJECT-TYPE
	SYNTAX     INTEGER {
		invalid(1), valid(2), unknown(3)
	}
	MAX-ACCESS read-only
	STATUS     current
	DESCRIPTION
		"This shows the validity of information of partition8."
	::= { partition8BasicInfo 1 }

partition8MaxCurrent                     OBJECT-TYPE
	SYNTAX     Integer32
	UNITS      "0.1 A"
	MAX-ACCESS read-only
	STATUS     current
	DESCRIPTION
		"This shows the maximum current of partition8."
	::= { partition8BasicInfo 2 }

partition8MaxPower                       OBJECT-TYPE
	SYNTAX     Integer32
	UNITS      "W"
	MAX-ACCESS read-only
	STATUS     current
	DESCRIPTION
		"This shows the maximum power of partition8."
	::= { partition8BasicInfo 3 }

partition8ProcCoreCount                  OBJECT-TYPE
	SYNTAX     Integer32
	MAX-ACCESS read-only
	STATUS     current
	DESCRIPTION
		"This shows the total number of CPU core of partition8."
	::= { partition8BasicInfo 4 }

partition8DIMMCapacity                   OBJECT-TYPE
	SYNTAX     Integer32
	UNITS      "GB"
	MAX-ACCESS read-only
	STATUS     current
	DESCRIPTION
		"This shows the total amount of DIMM capacity of partition8."
	::= { partition8BasicInfo 5 }

partition8HVMLicence                     OBJECT-TYPE
	SYNTAX     DisplayString
	MAX-ACCESS read-only
	STATUS     current
	DESCRIPTION
		"This shows the HVM licence information of partition8."
	::= { partition8BasicInfo 6 }

partition8Settings                       OBJECT IDENTIFIER ::= { partition8 3 }

partition8SettingsSystemMode             OBJECT-TYPE
	SYNTAX     INTEGER {
		basic(1), hvm(2), unknown(3)
	}
	MAX-ACCESS read-only
	STATUS     current
	DESCRIPTION
		"This shows the hvm mode setting of partition8."
	::= { partition8Settings 1 }

partition8SettingsDIMMRedundancy         OBJECT-TYPE
	SYNTAX     INTEGER {
		redundancy(1), non-redundancy(2), unknown(3)
	}
	MAX-ACCESS read-only
	STATUS     current
	DESCRIPTION
		"This shows the DIMM redundancy of partition8."
	::= { partition8Settings 2 }

partition8State                          OBJECT IDENTIFIER ::= { partition8 4 }

partition8StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition8."
	::= { partition8State 1 }

partition8StateHealth                    OBJECT-TYPE
	SYNTAX     INTEGER {
		normal(1), fail(2), unknown(3)
	}
	MAX-ACCESS read-only
	STATUS     current
	DESCRIPTION
		"This shows the health state of partition8."
	::= { partition8State 2 }

partition8StateSystemMode                OBJECT-TYPE
	SYNTAX     INTEGER {
		basic(1), hvm(2), unknown(3)
	}
	MAX-ACCESS read-only
	STATUS     current
	DESCRIPTION
		"This shows the hvm mode of partition8."
	::= { partition8State 3 }

partition8StateCunsumptionCurrent        OBJECT-TYPE
	SYNTAX     Integer32
	UNITS      "0.1 A"
	MAX-ACCESS read-only
	STATUS     current
	DESCRIPTION
		"This shows the consumption current of partition8."
	::= { partition8State 4 }

partition8StatePowerConsumption          OBJECT-TYPE
	SYNTAX     Integer32
	UNITS      "W"
	MAX-ACCESS read-only
	STATUS     current
	DESCRIPTION
		"This shows the current power consumption of partition8."
	::= { partition8State 5 }

partition9                               OBJECT IDENTIFIER ::= { partition 9 }

partition9BasicInfo                      OBJECT IDENTIFIER ::= { partition9 1 }

partition9Valid                          OBJECT-TYPE
	SYNTAX     INTEGER {
		invalid(1), valid(2), unknown(3)
	}
	MAX-ACCESS read-only
	STATUS     current
	DESCRIPTION
		"This shows the validity of information of partition9."
	::= { partition9BasicInfo 1 }

partition9MaxCurrent                     OBJECT-TYPE
	SYNTAX     Integer32
	UNITS      "0.1 A"
	MAX-ACCESS read-only
	STATUS     current
	DESCRIPTION
		"This shows the maximum current of partition9."
	::= { partition9BasicInfo 2 }

partition9MaxPower                       OBJECT-TYPE
	SYNTAX     Integer32
	UNITS      "W"
	MAX-ACCESS read-only
	STATUS     current
	DESCRIPTION
		"This shows the maximum power of partition9."
	::= { partition9BasicInfo 3 }

partition9ProcCoreCount                  OBJECT-TYPE
	SYNTAX     Integer32
	MAX-ACCESS read-only
	STATUS     current
	DESCRIPTION
		"This shows the total number of CPU core of partition9."
	::= { partition9BasicInfo 4 }

partition9DIMMCapacity                   OBJECT-TYPE
	SYNTAX     Integer32
	UNITS      "GB"
	MAX-ACCESS read-only
	STATUS     current
	DESCRIPTION
		"This shows the total amount of DIMM capacity of partition9."
	::= { partition9BasicInfo 5 }

partition9HVMLicence                     OBJECT-TYPE
	SYNTAX     DisplayString
	MAX-ACCESS read-only
	STATUS     current
	DESCRIPTION
		"This shows the HVM licence information of partition9."
	::= { partition9BasicInfo 6 }

partition9Settings                       OBJECT IDENTIFIER ::= { partition9 3 }

partition9SettingsSystemMode             OBJECT-TYPE
	SYNTAX     INTEGER {
		basic(1), hvm(2), unknown(3)
	}
	MAX-ACCESS read-only
	STATUS     current
	DESCRIPTION
		"This shows the hvm mode setting of partition9."
	::= { partition9Settings 1 }

partition9SettingsDIMMRedundancy         OBJECT-TYPE
	SYNTAX     INTEGER {
		redundancy(1), non-redundancy(2), unknown(3)
	}
	MAX-ACCESS read-only
	STATUS     current
	DESCRIPTION
		"This shows the DIMM redundancy of partition9."
	::= { partition9Settings 2 }

partition9State                          OBJECT IDENTIFIER ::= { partition9 4 }

partition9StatePower                     OBJECT-TYPE
	SYNTAX     INTEGER {
		poweroff(1), standby(2), poweron(3), unknown(4), poweron-executing(5), poweroff-executing(6)
	}
	MAX-ACCESS read-only
	STATUS     current
	DESCRIPTION
		"This shows the power supply state of partition9."
	::= { partition9State 1 }

partition9StateHealth                    OBJECT-TYPE
	SYNTAX     INTEGER {
		normal(1), fail(2), unknown(3)
	}
	MAX-ACCESS read-only
	STATUS     current
	DESCRIPTION
		"This shows the health state of partition9."
	::= { partition9State 2 }

partition9StateSystemMode                OBJECT-TYPE
	SYNTAX     INTEGER {
		basic(1), hvm(2), unknown(3)
	}
	MAX-ACCESS read-only
	STATUS     current
	DESCRIPTION
		"This shows the hvm mode of partition9."
	::= { partition9State 3 }

partition9StateCunsumptionCurrent        OBJECT-TYPE
	SYNTAX     Integer32
	UNITS      "0.1 A"
	MAX-ACCESS read-only
	STATUS     current
	DESCRIPTION
		"This shows the consumption current of partition9."
	::= { partition9State 4 }

partition9StatePowerConsumption          OBJECT-TYPE
	SYNTAX     Integer32
	UNITS      "W"
	MAX-ACCESS read-only
	STATUS     current
	DESCRIPTION
		"This shows the current power consumption of partition9."
	::= { partition9State 5 }

partition10                              OBJECT IDENTIFIER ::= { partition 10 }

partition10BasicInfo                     OBJECT IDENTIFIER ::= { partition10 1 }

partition10Valid                         OBJECT-TYPE
	SYNTAX     INTEGER {
		invalid(1), valid(2), unknown(3)
	}
	MAX-ACCESS read-only
	STATUS     current
	DESCRIPTION
		"This shows the validity of information of partition10."
	::= { partition10BasicInfo 1 }

partition10MaxCurrent                    OBJECT-TYPE
	SYNTAX     Integer32
	UNITS      "0.1 A"
	MAX-ACCESS read-only
	STATUS     current
	DESCRIPTION
		"This shows the maximum current of partition10."
	::= { partition10BasicInfo 2 }

partition10MaxPower                      OBJECT-TYPE
	SYNTAX     Integer32
	UNITS      "W"
	MAX-ACCESS read-only
	STATUS     current
	DESCRIPTION
		"This shows the maximum power of partition10."
	::= { partition10BasicInfo 3 }

partition10ProcCoreCount                 OBJECT-TYPE
	SYNTAX     Integer32
	MAX-ACCESS read-only
	STATUS     current
	DESCRIPTION
		"This shows the total number of CPU core of partition10."
	::= { partition10BasicInfo 4 }

partition10DIMMCapacity                  OBJECT-TYPE
	SYNTAX     Integer32
	UNITS      "GB"
	MAX-ACCESS read-only
	STATUS     current
	DESCRIPTION
		"This shows the total amount of DIMM capacity of partition10."
	::= { partition10BasicInfo 5 }

partition10HVMLicence                    OBJECT-TYPE
	SYNTAX     DisplayString
	MAX-ACCESS read-only
	STATUS     current
	DESCRIPTION
		"This shows the HVM licence information of partition10."
	::= { partition10BasicInfo 6 }

partition10Settings                      OBJECT IDENTIFIER ::= { partition10 3 }

partition10SettingsSystemMode            OBJECT-TYPE
	SYNTAX     INTEGER {
		basic(1), hvm(2), unknown(3)
	}
	MAX-ACCESS read-only
	STATUS     current
	DESCRIPTION
		"This shows the hvm mode setting of partition10."
	::= { partition10Settings 1 }

partition10SettingsDIMMRedundancy        OBJECT-TYPE
	SYNTAX     INTEGER {
		redundancy(1), non-redundancy(2), unknown(3)
	}
	MAX-ACCESS read-only
	STATUS     current
	DESCRIPTION
		"This shows the DIMM redundancy of partition10."
	::= { partition10Settings 2 }

partition10State                         OBJECT IDENTIFIER ::= { partition10 4 }

partition10StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition10."
	::= { partition10State 1 }

partition10StateHealth                   OBJECT-TYPE
	SYNTAX     INTEGER {
		normal(1), fail(2), unknown(3)
	}
	MAX-ACCESS read-only
	STATUS     current
	DESCRIPTION
		"This shows the health state of partition10."
	::= { partition10State 2 }

partition10StateSystemMode               OBJECT-TYPE
	SYNTAX     INTEGER {
		basic(1), hvm(2), unknown(3)
	}
	MAX-ACCESS read-only
	STATUS     current
	DESCRIPTION
		"This shows the hvm mode of partition10."
	::= { partition10State 3 }

partition10StateCunsumptionCurrent       OBJECT-TYPE
	SYNTAX     Integer32
	UNITS      "0.1 A"
	MAX-ACCESS read-only
	STATUS     current
	DESCRIPTION
		"This shows the consumption current of partition10."
	::= { partition10State 4 }

partition10StatePowerConsumption         OBJECT-TYPE
	SYNTAX     Integer32
	UNITS      "W"
	MAX-ACCESS read-only
	STATUS     current
	DESCRIPTION
		"This shows the current power consumption of partition10."
	::= { partition10State 5 }

partition11                              OBJECT IDENTIFIER ::= { partition 11 }

partition11BasicInfo                     OBJECT IDENTIFIER ::= { partition11 1 }

partition11Valid                         OBJECT-TYPE
	SYNTAX     INTEGER {
		invalid(1), valid(2), unknown(3)
	}
	MAX-ACCESS read-only
	STATUS     current
	DESCRIPTION
		"This shows the validity of information of partition11."
	::= { partition11BasicInfo 1 }

partition11MaxCurrent                    OBJECT-TYPE
	SYNTAX     Integer32
	UNITS      "0.1 A"
	MAX-ACCESS read-only
	STATUS     current
	DESCRIPTION
		"This shows the maximum current of partition11."
	::= { partition11BasicInfo 2 }

partition11MaxPower                      OBJECT-TYPE
	SYNTAX     Integer32
	UNITS      "W"
	MAX-ACCESS read-only
	STATUS     current
	DESCRIPTION
		"This shows the maximum power of partition11."
	::= { partition11BasicInfo 3 }

partition11ProcCoreCount                 OBJECT-TYPE
	SYNTAX     Integer32
	MAX-ACCESS read-only
	STATUS     current
	DESCRIPTION
		"This shows the total number of CPU core of partition11."
	::= { partition11BasicInfo 4 }

partition11DIMMCapacity                  OBJECT-TYPE
	SYNTAX     Integer32
	UNITS      "GB"
	MAX-ACCESS read-only
	STATUS     current
	DESCRIPTION
		"This shows the total amount of DIMM capacity of partition11."
	::= { partition11BasicInfo 5 }

partition11HVMLicence                    OBJECT-TYPE
	SYNTAX     DisplayString
	MAX-ACCESS read-only
	STATUS     current
	DESCRIPTION
		"This shows the HVM licence information of partition11."
	::= { partition11BasicInfo 6 }

partition11Settings                      OBJECT IDENTIFIER ::= { partition11 3 }

partition11SettingsSystemMode            OBJECT-TYPE
	SYNTAX     INTEGER {
		basic(1), hvm(2), unknown(3)
	}
	MAX-ACCESS read-only
	STATUS     current
	DESCRIPTION
		"This shows the hvm mode setting of partition11."
	::= { partition11Settings 1 }

partition11SettingsDIMMRedundancy        OBJECT-TYPE
	SYNTAX     INTEGER {
		redundancy(1), non-redundancy(2), unknown(3)
	}
	MAX-ACCESS read-only
	STATUS     current
	DESCRIPTION
		"This shows the DIMM redundancy of partition11."
	::= { partition11Settings 2 }

partition11State                         OBJECT IDENTIFIER ::= { partition11 4 }

partition11StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition11."
	::= { partition11State 1 }

partition11StateHealth                   OBJECT-TYPE
	SYNTAX     INTEGER {
		normal(1), fail(2), unknown(3)
	}
	MAX-ACCESS read-only
	STATUS     current
	DESCRIPTION
		"This shows the health state of partition11."
	::= { partition11State 2 }

partition11StateSystemMode               OBJECT-TYPE
	SYNTAX     INTEGER {
		basic(1), hvm(2), unknown(3)
	}
	MAX-ACCESS read-only
	STATUS     current
	DESCRIPTION
		"This shows the hvm mode of partition11."
	::= { partition11State 3 }

partition11StateCunsumptionCurrent       OBJECT-TYPE
	SYNTAX     Integer32
	UNITS      "0.1 A"
	MAX-ACCESS read-only
	STATUS     current
	DESCRIPTION
		"This shows the consumption current of partition11."
	::= { partition11State 4 }

partition11StatePowerConsumption         OBJECT-TYPE
	SYNTAX     Integer32
	UNITS      "W"
	MAX-ACCESS read-only
	STATUS     current
	DESCRIPTION
		"This shows the current power consumption of partition11."
	::= { partition11State 5 }

partition12                              OBJECT IDENTIFIER ::= { partition 12 }

partition12BasicInfo                     OBJECT IDENTIFIER ::= { partition12 1 }

partition12Valid                         OBJECT-TYPE
	SYNTAX     INTEGER {
		invalid(1), valid(2), unknown(3)
	}
	MAX-ACCESS read-only
	STATUS     current
	DESCRIPTION
		"This shows the validity of information of partition12."
	::= { partition12BasicInfo 1 }

partition12MaxCurrent                    OBJECT-TYPE
	SYNTAX     Integer32
	UNITS      "0.1 A"
	MAX-ACCESS read-only
	STATUS     current
	DESCRIPTION
		"This shows the maximum current of partition12."
	::= { partition12BasicInfo 2 }

partition12MaxPower                      OBJECT-TYPE
	SYNTAX     Integer32
	UNITS      "W"
	MAX-ACCESS read-only
	STATUS     current
	DESCRIPTION
		"This shows the maximum power of partition12."
	::= { partition12BasicInfo 3 }

partition12ProcCoreCount                 OBJECT-TYPE
	SYNTAX     Integer32
	MAX-ACCESS read-only
	STATUS     current
	DESCRIPTION
		"This shows the total number of CPU core of partition12."
	::= { partition12BasicInfo 4 }

partition12DIMMCapacity                  OBJECT-TYPE
	SYNTAX     Integer32
	UNITS      "GB"
	MAX-ACCESS read-only
	STATUS     current
	DESCRIPTION
		"This shows the total amount of DIMM capacity of partition12."
	::= { partition12BasicInfo 5 }

partition12HVMLicence                    OBJECT-TYPE
	SYNTAX     DisplayString
	MAX-ACCESS read-only
	STATUS     current
	DESCRIPTION
		"This shows the HVM licence information of partition12."
	::= { partition12BasicInfo 6 }

partition12Settings                      OBJECT IDENTIFIER ::= { partition12 3 }

partition12SettingsSystemMode            OBJECT-TYPE
	SYNTAX     INTEGER {
		basic(1), hvm(2), unknown(3)
	}
	MAX-ACCESS read-only
	STATUS     current
	DESCRIPTION
		"This shows the hvm mode setting of partition12."
	::= { partition12Settings 1 }

partition12SettingsDIMMRedundancy        OBJECT-TYPE
	SYNTAX     INTEGER {
		redundancy(1), non-redundancy(2), unknown(3)
	}
	MAX-ACCESS read-only
	STATUS     current
	DESCRIPTION
		"This shows the DIMM redundancy of partition12."
	::= { partition12Settings 2 }

partition12State                         OBJECT IDENTIFIER ::= { partition12 4 }

partition12StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition12."
	::= { partition12State 1 }

partition12StateHealth                   OBJECT-TYPE
	SYNTAX     INTEGER {
		normal(1), fail(2), unknown(3)
	}
	MAX-ACCESS read-only
	STATUS     current
	DESCRIPTION
		"This shows the health state of partition12."
	::= { partition12State 2 }

partition12StateSystemMode               OBJECT-TYPE
	SYNTAX     INTEGER {
		basic(1), hvm(2), unknown(3)
	}
	MAX-ACCESS read-only
	STATUS     current
	DESCRIPTION
		"This shows the hvm mode of partition12."
	::= { partition12State 3 }

partition12StateCunsumptionCurrent       OBJECT-TYPE
	SYNTAX     Integer32
	UNITS      "0.1 A"
	MAX-ACCESS read-only
	STATUS     current
	DESCRIPTION
		"This shows the consumption current of partition12."
	::= { partition12State 4 }

partition12StatePowerConsumption         OBJECT-TYPE
	SYNTAX     Integer32
	UNITS      "W"
	MAX-ACCESS read-only
	STATUS     current
	DESCRIPTION
		"This shows the current power consumption of partition12."
	::= { partition12State 5 }

partition13                              OBJECT IDENTIFIER ::= { partition 13 }

partition13BasicInfo                     OBJECT IDENTIFIER ::= { partition13 1 }

partition13Valid                         OBJECT-TYPE
	SYNTAX     INTEGER {
		invalid(1), valid(2), unknown(3)
	}
	MAX-ACCESS read-only
	STATUS     current
	DESCRIPTION
		"This shows the validity of information of partition13."
	::= { partition13BasicInfo 1 }

partition13MaxCurrent                    OBJECT-TYPE
	SYNTAX     Integer32
	UNITS      "0.1 A"
	MAX-ACCESS read-only
	STATUS     current
	DESCRIPTION
		"This shows the maximum current of partition13."
	::= { partition13BasicInfo 2 }

partition13MaxPower                      OBJECT-TYPE
	SYNTAX     Integer32
	UNITS      "W"
	MAX-ACCESS read-only
	STATUS     current
	DESCRIPTION
		"This shows the maximum power of partition13."
	::= { partition13BasicInfo 3 }

partition13ProcCoreCount                 OBJECT-TYPE
	SYNTAX     Integer32
	MAX-ACCESS read-only
	STATUS     current
	DESCRIPTION
		"This shows the total number of CPU core of partition13."
	::= { partition13BasicInfo 4 }

partition13DIMMCapacity                  OBJECT-TYPE
	SYNTAX     Integer32
	UNITS      "GB"
	MAX-ACCESS read-only
	STATUS     current
	DESCRIPTION
		"This shows the total amount of DIMM capacity of partition13."
	::= { partition13BasicInfo 5 }

partition13HVMLicence                    OBJECT-TYPE
	SYNTAX     DisplayString
	MAX-ACCESS read-only
	STATUS     current
	DESCRIPTION
		"This shows the HVM licence information of partition13."
	::= { partition13BasicInfo 6 }

partition13Settings                      OBJECT IDENTIFIER ::= { partition13 3 }

partition13SettingsSystemMode            OBJECT-TYPE
	SYNTAX     INTEGER {
		basic(1), hvm(2), unknown(3)
	}
	MAX-ACCESS read-only
	STATUS     current
	DESCRIPTION
		"This shows the hvm mode setting of partition13."
	::= { partition13Settings 1 }

partition13SettingsDIMMRedundancy        OBJECT-TYPE
	SYNTAX     INTEGER {
		redundancy(1), non-redundancy(2), unknown(3)
	}
	MAX-ACCESS read-only
	STATUS     current
	DESCRIPTION
		"This shows the DIMM redundancy of partition13."
	::= { partition13Settings 2 }

partition13State                         OBJECT IDENTIFIER ::= { partition13 4 }

partition13StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition13."
	::= { partition13State 1 }

partition13StateHealth                   OBJECT-TYPE
	SYNTAX     INTEGER {
		normal(1), fail(2), unknown(3)
	}
	MAX-ACCESS read-only
	STATUS     current
	DESCRIPTION
		"This shows the health state of partition13."
	::= { partition13State 2 }

partition13StateSystemMode               OBJECT-TYPE
	SYNTAX     INTEGER {
		basic(1), hvm(2), unknown(3)
	}
	MAX-ACCESS read-only
	STATUS     current
	DESCRIPTION
		"This shows the hvm mode of partition13."
	::= { partition13State 3 }

partition13StateCunsumptionCurrent       OBJECT-TYPE
	SYNTAX     Integer32
	UNITS      "0.1 A"
	MAX-ACCESS read-only
	STATUS     current
	DESCRIPTION
		"This shows the consumption current of partition13."
	::= { partition13State 4 }

partition13StatePowerConsumption         OBJECT-TYPE
	SYNTAX     Integer32
	UNITS      "W"
	MAX-ACCESS read-only
	STATUS     current
	DESCRIPTION
		"This shows the current power consumption of partition13."
	::= { partition13State 5 }

partition14                              OBJECT IDENTIFIER ::= { partition 14 }

partition14BasicInfo                     OBJECT IDENTIFIER ::= { partition14 1 }

partition14Valid                         OBJECT-TYPE
	SYNTAX     INTEGER {
		invalid(1), valid(2), unknown(3)
	}
	MAX-ACCESS read-only
	STATUS     current
	DESCRIPTION
		"This shows the validity of information of partition14."
	::= { partition14BasicInfo 1 }

partition14MaxCurrent                    OBJECT-TYPE
	SYNTAX     Integer32
	UNITS      "0.1 A"
	MAX-ACCESS read-only
	STATUS     current
	DESCRIPTION
		"This shows the maximum current of partition14."
	::= { partition14BasicInfo 2 }

partition14MaxPower                      OBJECT-TYPE
	SYNTAX     Integer32
	UNITS      "W"
	MAX-ACCESS read-only
	STATUS     current
	DESCRIPTION
		"This shows the maximum power of partition14."
	::= { partition14BasicInfo 3 }

partition14ProcCoreCount                 OBJECT-TYPE
	SYNTAX     Integer32
	MAX-ACCESS read-only
	STATUS     current
	DESCRIPTION
		"This shows the total number of CPU core of partition14."
	::= { partition14BasicInfo 4 }

partition14DIMMCapacity                  OBJECT-TYPE
	SYNTAX     Integer32
	UNITS      "GB"
	MAX-ACCESS read-only
	STATUS     current
	DESCRIPTION
		"This shows the total amount of DIMM capacity of partition14."
	::= { partition14BasicInfo 5 }

partition14HVMLicence                    OBJECT-TYPE
	SYNTAX     DisplayString
	MAX-ACCESS read-only
	STATUS     current
	DESCRIPTION
		"This shows the HVM licence information of partition14."
	::= { partition14BasicInfo 6 }

partition14Settings                      OBJECT IDENTIFIER ::= { partition14 3 }

partition14SettingsSystemMode            OBJECT-TYPE
	SYNTAX     INTEGER {
		basic(1), hvm(2), unknown(3)
	}
	MAX-ACCESS read-only
	STATUS     current
	DESCRIPTION
		"This shows the hvm mode setting of partition14."
	::= { partition14Settings 1 }

partition14SettingsDIMMRedundancy        OBJECT-TYPE
	SYNTAX     INTEGER {
		redundancy(1), non-redundancy(2), unknown(3)
	}
	MAX-ACCESS read-only
	STATUS     current
	DESCRIPTION
		"This shows the DIMM redundancy of partition14."
	::= { partition14Settings 2 }

partition14State                         OBJECT IDENTIFIER ::= { partition14 4 }

partition14StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition14."
	::= { partition14State 1 }

partition14StateHealth                   OBJECT-TYPE
	SYNTAX     INTEGER {
		normal(1), fail(2), unknown(3)
	}
	MAX-ACCESS read-only
	STATUS     current
	DESCRIPTION
		"This shows the health state of partition14."
	::= { partition14State 2 }

partition14StateSystemMode               OBJECT-TYPE
	SYNTAX     INTEGER {
		basic(1), hvm(2), unknown(3)
	}
	MAX-ACCESS read-only
	STATUS     current
	DESCRIPTION
		"This shows the hvm mode of partition14."
	::= { partition14State 3 }

partition14StateCunsumptionCurrent       OBJECT-TYPE
	SYNTAX     Integer32
	UNITS      "0.1 A"
	MAX-ACCESS read-only
	STATUS     current
	DESCRIPTION
		"This shows the consumption current of partition14."
	::= { partition14State 4 }

partition14StatePowerConsumption         OBJECT-TYPE
	SYNTAX     Integer32
	UNITS      "W"
	MAX-ACCESS read-only
	STATUS     current
	DESCRIPTION
		"This shows the current power consumption of partition14."
	::= { partition14State 5 }

partition15                              OBJECT IDENTIFIER ::= { partition 15 }

partition15BasicInfo                     OBJECT IDENTIFIER ::= { partition15 1 }

partition15Valid                         OBJECT-TYPE
	SYNTAX     INTEGER {
		invalid(1), valid(2), unknown(3)
	}
	MAX-ACCESS read-only
	STATUS     current
	DESCRIPTION
		"This shows the validity of information of partition15."
	::= { partition15BasicInfo 1 }

partition15MaxCurrent                    OBJECT-TYPE
	SYNTAX     Integer32
	UNITS      "0.1 A"
	MAX-ACCESS read-only
	STATUS     current
	DESCRIPTION
		"This shows the maximum current of partition15."
	::= { partition15BasicInfo 2 }

partition15MaxPower                      OBJECT-TYPE
	SYNTAX     Integer32
	UNITS      "W"
	MAX-ACCESS read-only
	STATUS     current
	DESCRIPTION
		"This shows the maximum power of partition15."
	::= { partition15BasicInfo 3 }

partition15ProcCoreCount                 OBJECT-TYPE
	SYNTAX     Integer32
	MAX-ACCESS read-only
	STATUS     current
	DESCRIPTION
		"This shows the total number of CPU core of partition15."
	::= { partition15BasicInfo 4 }

partition15DIMMCapacity                  OBJECT-TYPE
	SYNTAX     Integer32
	UNITS      "GB"
	MAX-ACCESS read-only
	STATUS     current
	DESCRIPTION
		"This shows the total amount of DIMM capacity of partition15."
	::= { partition15BasicInfo 5 }

partition15HVMLicence                    OBJECT-TYPE
	SYNTAX     DisplayString
	MAX-ACCESS read-only
	STATUS     current
	DESCRIPTION
		"This shows the HVM licence information of partition15."
	::= { partition15BasicInfo 6 }

partition15Settings                      OBJECT IDENTIFIER ::= { partition15 3 }

partition15SettingsSystemMode            OBJECT-TYPE
	SYNTAX     INTEGER {
		basic(1), hvm(2), unknown(3)
	}
	MAX-ACCESS read-only
	STATUS     current
	DESCRIPTION
		"This shows the hvm mode setting of partition15."
	::= { partition15Settings 1 }

partition15SettingsDIMMRedundancy        OBJECT-TYPE
	SYNTAX     INTEGER {
		redundancy(1), non-redundancy(2), unknown(3)
	}
	MAX-ACCESS read-only
	STATUS     current
	DESCRIPTION
		"This shows the DIMM redundancy of partition15."
	::= { partition15Settings 2 }

partition15State                         OBJECT IDENTIFIER ::= { partition15 4 }

partition15StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition15."
	::= { partition15State 1 }

partition15StateHealth                   OBJECT-TYPE
	SYNTAX     INTEGER {
		normal(1), fail(2), unknown(3)
	}
	MAX-ACCESS read-only
	STATUS     current
	DESCRIPTION
		"This shows the health state of partition15."
	::= { partition15State 2 }

partition15StateSystemMode               OBJECT-TYPE
	SYNTAX     INTEGER {
		basic(1), hvm(2), unknown(3)
	}
	MAX-ACCESS read-only
	STATUS     current
	DESCRIPTION
		"This shows the hvm mode of partition15."
	::= { partition15State 3 }

partition15StateCunsumptionCurrent       OBJECT-TYPE
	SYNTAX     Integer32
	UNITS      "0.1 A"
	MAX-ACCESS read-only
	STATUS     current
	DESCRIPTION
		"This shows the consumption current of partition15."
	::= { partition15State 4 }

partition15StatePowerConsumption         OBJECT-TYPE
	SYNTAX     Integer32
	UNITS      "W"
	MAX-ACCESS read-only
	STATUS     current
	DESCRIPTION
		"This shows the current power consumption of partition15."
	::= { partition15State 5 }

partition16                              OBJECT IDENTIFIER ::= { partition 16 }

partition16BasicInfo                     OBJECT IDENTIFIER ::= { partition16 1 }

partition16Valid                         OBJECT-TYPE
	SYNTAX     INTEGER {
		invalid(1), valid(2), unknown(3)
	}
	MAX-ACCESS read-only
	STATUS     current
	DESCRIPTION
		"This shows the validity of information of partition16."
	::= { partition16BasicInfo 1 }

partition16MaxCurrent                    OBJECT-TYPE
	SYNTAX     Integer32
	UNITS      "0.1 A"
	MAX-ACCESS read-only
	STATUS     current
	DESCRIPTION
		"This shows the maximum current of partition16."
	::= { partition16BasicInfo 2 }

partition16MaxPower                      OBJECT-TYPE
	SYNTAX     Integer32
	UNITS      "W"
	MAX-ACCESS read-only
	STATUS     current
	DESCRIPTION
		"This shows the maximum power of partition16."
	::= { partition16BasicInfo 3 }

partition16ProcCoreCount                 OBJECT-TYPE
	SYNTAX     Integer32
	MAX-ACCESS read-only
	STATUS     current
	DESCRIPTION
		"This shows the total number of CPU core of partition16."
	::= { partition16BasicInfo 4 }

partition16DIMMCapacity                  OBJECT-TYPE
	SYNTAX     Integer32
	UNITS      "GB"
	MAX-ACCESS read-only
	STATUS     current
	DESCRIPTION
		"This shows the total amount of DIMM capacity of partition16."
	::= { partition16BasicInfo 5 }

partition16HVMLicence                    OBJECT-TYPE
	SYNTAX     DisplayString
	MAX-ACCESS read-only
	STATUS     current
	DESCRIPTION
		"This shows the HVM licence information of partition16."
	::= { partition16BasicInfo 6 }

partition16Settings                      OBJECT IDENTIFIER ::= { partition16 3 }

partition16SettingsSystemMode            OBJECT-TYPE
	SYNTAX     INTEGER {
		basic(1), hvm(2), unknown(3)
	}
	MAX-ACCESS read-only
	STATUS     current
	DESCRIPTION
		"This shows the hvm mode setting of partition16."
	::= { partition16Settings 1 }

partition16SettingsDIMMRedundancy        OBJECT-TYPE
	SYNTAX     INTEGER {
		redundancy(1), non-redundancy(2), unknown(3)
	}
	MAX-ACCESS read-only
	STATUS     current
	DESCRIPTION
		"This shows the DIMM redundancy of partition16."
	::= { partition16Settings 2 }

partition16State                         OBJECT IDENTIFIER ::= { partition16 4 }

partition16StatePower                    OBJECT-TYPE
	SYNTAX     INTEGER {
		poweroff(1), standby(2), poweron(3), unknown(4), poweron-executing(5), poweroff-executing(6)
	}
	MAX-ACCESS read-only
	STATUS     current
	DESCRIPTION
		"This shows the power supply state of partition16."
	::= { partition16State 1 }

partition16StateHealth                   OBJECT-TYPE
	SYNTAX     INTEGER {
		normal(1), fail(2), unknown(3)
	}
	MAX-ACCESS read-only
	STATUS     current
	DESCRIPTION
		"This shows the health state of partition16."
	::= { partition16State 2 }

partition16StateSystemMode               OBJECT-TYPE
	SYNTAX     INTEGER {
		basic(1), hvm(2), unknown(3)
	}
	MAX-ACCESS read-only
	STATUS     current
	DESCRIPTION
		"This shows the hvm mode of partition16."
	::= { partition16State 3 }

partition16StateCunsumptionCurrent       OBJECT-TYPE
	SYNTAX     Integer32
	UNITS      "0.1 A"
	MAX-ACCESS read-only
	STATUS     current
	DESCRIPTION
		"This shows the consumption current of partition16."
	::= { partition16State 4 }

partition16StatePowerConsumption         OBJECT-TYPE
	SYNTAX     Integer32
	UNITS      "W"
	MAX-ACCESS read-only
	STATUS     current
	DESCRIPTION
		"This shows the current power consumption of partition16."
	::= { partition16State 5 }

managementService                        OBJECT-TYPE
	SYNTAX     DisplayString
	MAX-ACCESS read-only
	STATUS     current
	DESCRIPTION
		"Reserved."
	::= { computeRack 4 }

control                                  OBJECT-TYPE
	SYNTAX     DisplayString
	MAX-ACCESS read-only
	STATUS     current
	DESCRIPTION
		"Reserved."
	::= { computeRack 5 }
-------------------------------------------------------------------------------
--*********
-- notification definitions
--*********

--------------------------------------------------------------------------------
--	alertTrap
--------------------------------------------------------------------------------

alertTrap
	OBJECT IDENTIFIER
	::=	{ compute 10 }

alertTrapCommon
	OBJECT IDENTIFIER
	::=	{ alertTrap 0 }

alertTrapInfLocalTime
	OBJECT-TYPE
	SYNTAX			DisplayString	(SIZE(0..28))
	MAX-ACCESS		read-only
	STATUS			current
	DESCRIPTION
		"VarBind01:LocalTime YYYY-MM-DD hh:mm:ss(+TZ)"
	::=	{ alertTrapCommon 1 }

alertTrapInfChassisID
	OBJECT-TYPE
	SYNTAX			DisplayString	(SIZE(0..16))
	MAX-ACCESS		read-only
	STATUS			current
	DESCRIPTION
		"VarBind02:ChassisID"
	::=	{ alertTrapCommon 2 }

alertTrapInfAlertLevel
	OBJECT-TYPE
	SYNTAX
		INTEGER
		{
			information	(1),
			warning		(2),
			error		(3),
			event		(4)
		}
	MAX-ACCESS		read-only
	STATUS			current
	DESCRIPTION		
		"VarBind03:AlertLevel
		1 = Information
		2 = Warning
		3 = Error
		4 = Event"
	::=	{ alertTrapCommon 3 }

alertTrapInfAlertID
	OBJECT-TYPE
	SYNTAX			DisplayString	(SIZE(0..4))
	MAX-ACCESS		read-only
	STATUS			current
	DESCRIPTION
		"VarBind04:AlertID"
	::=	{ alertTrapCommon 4 }

alertTrapInfAlertMessage
	OBJECT-TYPE
	SYNTAX			DisplayString	(SIZE(0..255))
	MAX-ACCESS		read-only
	STATUS			current
	DESCRIPTION
		"VarBind05:AlertMessage"
	::=	{ alertTrapCommon 5 }

alertTrapInfAlertOutbreakPart
	OBJECT-TYPE
	SYNTAX			DisplayString	(SIZE(0..2))
	MAX-ACCESS		read-only
	STATUS			current
	DESCRIPTION
		"VarBind06:AlertOutbreakPart
		00 = ServerModule
		01 = HDD Module
		02 = DVD Module
		03 = IOA
		04 = SVP Module
		05 = Power Supply Module
		06 = FAN Module
		07 = PCI Card
		08 = Partition
		09 = SW FAN Module
		10 = LAN SW Module
		11 = FC SW Module
		12 = Connector PK Module
		13 = Path Through SW Module
		14 = SAS SW Module
		15 = IOSW Module
		17 = I/O Board Module
		XX = Unknown"
	::=	{ alertTrapCommon 6 }

alertTrapInfAlertModuleType
	OBJECT-TYPE
	SYNTAX			DisplayString
	MAX-ACCESS		read-only
	STATUS			current
	DESCRIPTION
		"VarBind07:AlertModuleType"
	::=	{ alertTrapCommon 7 }

alertTrapInfAlertModuleLocation
	OBJECT-TYPE
	SYNTAX			DisplayString
	MAX-ACCESS		read-only
	STATUS			current
	DESCRIPTION
		"VarBind08:AlertModuleLocation"
	::=	{ alertTrapCommon 8 }

alertTrapInfAlertModuleModelName
	OBJECT-TYPE
	SYNTAX			DisplayString
	MAX-ACCESS		read-only
	STATUS			current
	DESCRIPTION
		"VarBind09:AlertModuleModelName"
	::=	{ alertTrapCommon 9 }

alertTrapInfAlertModuleSerialNum
	OBJECT-TYPE
	SYNTAX			DisplayString
	MAX-ACCESS		read-only
	STATUS			current
	DESCRIPTION
		"VarBind10:AlertModuleSerialNum"
	::=	{ alertTrapCommon 10 }

alertTrapInfAlertEventCode
	OBJECT-TYPE
	SYNTAX			DisplayString
	MAX-ACCESS		read-only
	STATUS			current
	DESCRIPTION
		"VarBind11:AlertEventCode"
	::=	{ alertTrapCommon 11 }

-------------------------------------------------------------------------------
-- BSX MIB
--------------------------------------------------------------------------------

bsm
	OBJECT IDENTIFIER
	::=	{ alertTrap 1 }

bsmAlertTrap
	OBJECT IDENTIFIER
	::=	{ bsm 1 }

--------------------------------------------------------------------------------

bsmAlertTrapSvp
	OBJECT IDENTIFIER
	::=	{ bsmAlertTrap 1 }

bsmAlertTrapSvpNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the fault level."
	::= { bsmAlertTrapSvp 1 }

bsmAlertTrapSvpSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the warning level."
	::= { bsmAlertTrapSvp 2 }

bsmAlertTrapSvpInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event of the information level."
	::= { bsmAlertTrapSvp 3 }

bsmAlertTrapSvpEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the management module encountered an event."
	::= { bsmAlertTrapSvp 4 }

--------------------------------------------------------------------------------

bsmAlertTrapBlade
	OBJECT IDENTIFIER
	::=	{ bsmAlertTrap 2 }

bsmAlertTrapBladeNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the fault level."
	::= { bsmAlertTrapBlade 1 }

bsmAlertTrapBladeSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the warning level."
	::= { bsmAlertTrapBlade 2 }

bsmAlertTrapBladeInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event of the information level."
	::= { bsmAlertTrapBlade 3 }

bsmAlertTrapBladeEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows the server blade encountered an event."
	::= { bsmAlertTrapBlade 4 }

--------------------------------------------------------------------------------

bsmAlertTrapOther
	OBJECT IDENTIFIER
	::=	{ bsmAlertTrap 20 }

bsmAlertTrapOtherNon-Recoverable
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the fault level."
	::= { bsmAlertTrapOther 1 }

bsmAlertTrapOtherSerious
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the warning level."
	::= { bsmAlertTrapOther 2 }

bsmAlertTrapOtherInformation
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event of the information level."
	::= { bsmAlertTrapOther 3 }

bsmAlertTrapOtherEvent
	NOTIFICATION-TYPE
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"This shows a location except management modules or server blades encountered an event."
	::= { bsmAlertTrapOther 4 }

--------------------------------------------------------------------------------

bsmMIBGroups
	OBJECT IDENTIFIER
	::=	{ bsm 100 }

bsmAlertTrapInfoGroup
	OBJECT-GROUP
	OBJECTS
	{
		alertTrapInfLocalTime ,
		alertTrapInfChassisID ,
		alertTrapInfAlertLevel ,
		alertTrapInfAlertID,
		alertTrapInfAlertMessage ,
		alertTrapInfAlertOutbreakPart
	}
	STATUS			current
	DESCRIPTION		"bsmAlertTrapInfoGroup"
	::= { bsmMIBGroups 1 }

bsmAlertTrapGroup
	NOTIFICATION-GROUP
	NOTIFICATIONS
	{
		bsmAlertTrapSvpNon-Recoverable ,
		bsmAlertTrapSvpSerious ,
		bsmAlertTrapSvpInformation ,
		bsmAlertTrapSvpEvent ,

		bsmAlertTrapBladeNon-Recoverable ,
		bsmAlertTrapBladeSerious ,
		bsmAlertTrapBladeInformation ,
		bsmAlertTrapBladeEvent ,

		bsmAlertTrapOtherNon-Recoverable ,
		bsmAlertTrapOtherSerious ,
		bsmAlertTrapOtherInformation ,
		bsmAlertTrapOtherEvent
	}
	STATUS			current
	DESCRIPTION		"bsmAlertTrapGroup"
	::= { bsmMIBGroups 2 }

--------------------------------------------------------------------------------

hcsm
	OBJECT IDENTIFIER
	::=	{ alertTrap 2 }

hcsmAlertTrap
	OBJECT IDENTIFIER
	::=	{ hcsm 1 }

--------------------------------------------------------------------------------

hcsmAlertTrapMonitoring
	OBJECT IDENTIFIER
	::=	{ hcsmAlertTrap 1 }

hcsmAlertTrapMonitoringError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as monitoring alert."
	::= { hcsmAlertTrapMonitoring 1 }

hcsmAlertTrapMonitoringWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as monitoring alert."
	::= { hcsmAlertTrapMonitoring 2 }

hcsmAlertTrapMonitoringInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as monitoring alert."
	::= { hcsmAlertTrapMonitoring 3 }

--------------------------------------------------------------------------------

hcsmAlertTrapEvent
	OBJECT IDENTIFIER
	::=	{ hcsmAlertTrap 2 }

hcsmAlertTrapEventError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as event alert."
	::= { hcsmAlertTrapEvent 1 }

hcsmAlertTrapEventWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as event alert."
	::= { hcsmAlertTrapEvent 2 }

hcsmAlertTrapEventInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as event alert."
	::= { hcsmAlertTrapEvent 3 }

--------------------------------------------------------------------------------

hcsmAlertTrapStatusChange
	OBJECT IDENTIFIER
	::=	{ hcsmAlertTrap 3 }

hcsmAlertTrapStatusChangeError
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the fault level was encountered as state change alert."
	::= { hcsmAlertTrapStatusChange 1 }

hcsmAlertTrapStatusChangeWarning
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the warning level was encountered as state change alert."
	::= { hcsmAlertTrapStatusChange 2 }

hcsmAlertTrapStatusChangeInformation
	NOTIFICATION-TYPE
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"This shows the event of the information level was encountered as state change alert."
	::= { hcsmAlertTrapStatusChange 3 }

--------------------------------------------------------------------------------

hcsmMIBGroups
	OBJECT IDENTIFIER
	::=	{ hcsm 100 }

hcsmAlertTrapInfoGroup
	OBJECT-GROUP
	OBJECTS
	{
		alertTrapInfLocalTime ,
		alertTrapInfChassisID ,
		alertTrapInfAlertLevel ,
		alertTrapInfAlertID,
		alertTrapInfAlertMessage ,
		alertTrapInfAlertModuleType ,
		alertTrapInfAlertModuleLocation ,
		alertTrapInfAlertModuleModelName ,
		alertTrapInfAlertModuleSerialNum ,
		alertTrapInfAlertEventCode
	}
	STATUS			current
	DESCRIPTION		"hcsmAlertTrapInfoGroup"
	::= { hcsmMIBGroups 1 }

hcsmAlertTrapGroup
	NOTIFICATION-GROUP
	NOTIFICATIONS
	{
		hcsmAlertTrapMonitoringError ,
		hcsmAlertTrapMonitoringWarning ,
		hcsmAlertTrapMonitoringInformation ,

		hcsmAlertTrapEventError ,
		hcsmAlertTrapEventWarning ,
		hcsmAlertTrapEventInformation ,

		hcsmAlertTrapStatusChangeError ,
		hcsmAlertTrapStatusChangeWarning ,
		hcsmAlertTrapStatusChangeInformation
	}
	STATUS			current
	DESCRIPTION		"hcsmAlertTrapGroup"
	::= { hcsmMIBGroups 2 }


-------------------------------------------------------------------------------

END
