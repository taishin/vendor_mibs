ARCserve-Alarm-MIB DEFINITIONS ::= BEGIN

	IMPORTS
		enterprises    FROM RFC1065-SMI
		OBJECT-TYPE    FROM RFC-1212
		TRAP-TYPE      FROM RFC-1215;
		
		cheyenne            OBJECT IDENTIFIER ::= { enterprises 46 }
		arcServe            OBJECT IDENTIFIER ::= { cheyenne 877 }
                arcServeNLMRev      OBJECT IDENTIFIER ::= { arcServe 1 }

-- *************************************************************************
-- ARCserve (1.3.6.1.4.1.46.877)
-- **************************************************************************
arcServeNLMRevMajor OBJECT-TYPE
	SYNTAX INTEGER (0..65535)
	ACCESS read-only
	STATUS mandatory
	DESCRIPTION
		"The major revision level of the NLM (left of the decimal).
		Used for presence checking."
	::= { arcServeNLMRev 1 }

arcServeNLMRevMinor OBJECT-TYPE
	SYNTAX INTEGER (0..65535)
	ACCESS read-only
	STATUS mandatory
	DESCRIPTION
		"The minor revision level of the NLM (right of the decimal)."
	::= { arcServeNLMRev 2 }

arcServeParmsTrapEnable OBJECT-TYPE
	SYNTAX INTEGER (0..1)
	ACCESS read-write
	STATUS mandatory
	DESCRIPTION
		"Indicates whether agent should or should not send traps."
	::= { arcServe 2 }

arcServeParmsPollTime OBJECT-TYPE
	SYNTAX INTEGER (60..2592000)
	ACCESS read-write
	STATUS mandatory
	DESCRIPTION
		"Seconds between checking for traps."
	::= { arcServe 3 }

arcServeServerName OBJECT-TYPE
                SYNTAX OCTET STRING
                ACCESS read-only
                STATUS mandatory
                DESCRIPTION
                        "NetWare Server Which Generated Error"
                ::= {arcServe 4}        
        
arcServetrapdesc   OBJECT-TYPE
                SYNTAX OCTET STRING
                ACCESS read-only
                STATUS optional
                DESCRIPTION
                        "A description of a specific Cheyenne trap"
                ::= {arcServe 5}        
        
-- *************************************************************************
-- traps
-- **************************************************************************
arcServetrapHigh                TRAP-TYPE       
	        		ENTERPRISE	arcServe
                                VARIABLES       {
                                                arcServeServerName,
                                                arcServetrapdesc
                                                }
        			DESCRIPTION
                                        "ARCserve Critical Trap."
                                --#TYPE "ARCserve Critical"
                                --#SUMMARY "%s  ARCserve: %s "
                                --#ARGUMENTS {0,1}
                                --#SEVERITY CRITICAL
                                --#STATE   DEGRADED     
	        	        ::= 1
arcServetrapMed                 TRAP-TYPE       
	        		ENTERPRISE	arcServe
                                VARIABLES       {
                                                arcServeServerName,
                                                arcServetrapdesc
                                                }
        			DESCRIPTION
                                        "ARCserve Minor Trap"
                                --#TYPE "ARCserve Warning"
                                --#SUMMARY "%s  ARCserve: %s "
                                --#ARGUMENTS {0,1}
                                --#SEVERITY MINOR
                                --#TIMEINDEX 1
                                --#STATE   OPERATIONAL     
	        	        ::= 2
arcServetrapLow                 TRAP-TYPE       
	        		ENTERPRISE	arcServe
                                VARIABLES       {
                                                arcServeServerName,
                                                arcServetrapdesc
                                                }
        			DESCRIPTION
                                        "ARCserve Informational Trap"
                                --#TYPE "ARCserve Informational"
                                --#SUMMARY "%s  ARCserve: %s "
                                --#ARGUMENTS {0,1}
                                --#SEVERITY INFORMATIONAL
                                --#STATE   OPERATIONAL     
	        	        ::= 3
END
